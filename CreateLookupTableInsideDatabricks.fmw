FME workspace CreateLookupTableInsideDatabricks.fmw
Title: Add Azure Blob file towards Microsoft SQL Datawarehouse
Description: To make the Lookup tables available inside the SQL Datawarehouse engine on Azure.
History: 05/05/2016,Jan Bliki,Initial creation

Parameters:
- LookupId =

Note: A Master Key is required in order to make this work. / This Needs to be done only once... / -- A: Create Master Key / -- Required to encrypt the credential secret in the next step. / CREATE MASTER KEY;
Creator
    GEOMTYPE = Geometry Object
    NUM = 1
    CREATED -> AttributeCreator_6
AttributeCreator_16
    ATTR_TABLE:
      SET_TO MessageString = Error Running CREATELOOKUPDATAFRAME notebook
        Cmd:@Value(cmd) Error: @Value(error)
        WorkSpace: $(WORKSPACE_NAME)

      SET_TO TransformerPath = CREATE_LOOKUP_IN_TEAL\SQLExecutor_4
      SET_TO _error = Error Running CREATELOOKUPDATAFRAME notebook
        Cmd:@Value(cmd) Error: @Value(error)
        WorkSpace: $(WORKSPACE_NAME)
    -> StringReplacer
AttributeCreator_3
    ATTR_TABLE:
      SET_TO MessageString = CreateLookupDataFrame Completed
      SET_TO TransformerPath = CreateLookupDataFrame
    -> AttributeCreator_16_OUTPUT_-__AttributeCreator_INFO
AttributeCreator_19
    ATTR_TABLE:
      SET_TO MessageString = Starting CreateLookupDataFrame Notebook
      SET_TO TransformerPath = CreateLookupDataFrame
    -> AttributeCreator_16_OUTPUT_-__AttributeCreator_INFO
AttributeCreator_2
    ATTR_TABLE:
      SET_TO MessageString = ERROR Could not get info on Lookup: @Value(LookupId)
      SET_TO TransformerPath = RETRIEVE_DETAILS
    -> AttributeCreator_2_OUTPUT_-__AttributeCreator_2_OUTPUT_-__AttributeCreator_ERROR
Terminator_2 [off]
    MESSAGE = Translation Terminated
AttributeCreator
    ATTR_TABLE:
      SET_TO MessageString = ERROR updating fme job id: @Value(_FME_JOB_ID)
      SET_TO TransformerPath = TELL_DB
    -> AttributeCreator_2_OUTPUT_-__AttributeCreator_2_OUTPUT_-__AttributeCreator_ERROR
AttributeCreator_2_OUTPUT_-__AttributeCreator_2_OUTPUT_-__AttributeCreator_ERROR: Junction
    -> AttributeCreator_2_OUTPUT_-__AttributeCreator_ERROR

Bookmark: Tell DB we are executing the job
Note: Reset the database and provide the job_id so log information can be found easily.
AttributeCreator_6
    ATTR_TABLE:
      SET_TO _FME_JOB_ID = FME_CONDITIONAL:DEFAULT_VALUE'$(FME_JOB_ID)'BOOL_OP;AND;COMPOSITE_TEST;<Unused>;TEST $(FME_JOB_ID) ATTRIBUTE_IS_MISSING _FME_BLANK_STRING_;TEST $(FME_JOB_ID) NOT_ATTRIBUTE_HAS_VALUE _FME_BLANK_STRING_'-1'FME_NUM_CONDITIONS2___
      SET_TO LookupId = $(LookupId)
    -> SQLExecutor [INITIATOR]
SQLExecutor
    COMBINE_ATTRS = Result Attributes Only
    COMBINE_GEOM = Initiator Geometry Only
    DATASET = CubeManager
    FORMAT = MSSQL_ADO
    MSSQL_ADO_COMMAND_TIMEOUT = 30
    MSSQL_ADO_CREATE_FEATURE_TABLES_FROM_DATA = Yes
    MSSQL_ADO_NAMED_CONNECTION = CubeManager
    MSSQL_ADO_QUERY_FEATURE_TYPES_FOR_MERGE_FILTERS = Yes
    SQL_STATEMENT:
      UPDATE dbo.Lookups
          set FMEJobIdSQLDWCreated = @Value(_FME_JOB_ID)
      WHERE LookupId = @Value(LookupId)
    INITIATOR -> GetMetaInfo [INITIATOR]
    <REJECTED> -> Logger [off]
    <REJECTED> -> AttributeCreator
Logger [off]
    MAXCOORDS = 20
    MAXFEATS = 20
    MESSAGE = ERROR updating fme job id:
    LOGGED -> Terminator_2 [off]

Bookmark: Retrieve details from DB
GetMetaInfo: SQLExecutor
    COMBINE_ATTRS = Keep Initiator Attributes if Conflict
    COMBINE_GEOM = Initiator Geometry Only
    DATASET = CubeManager
    EXPOSED_ATTRIBUTE_LIST = AzureLookupFile FieldAlias FieldName FieldType FileDay FileMonth FileYear IgnoreField Name SQLDWTableName
    FORMAT = MSSQL_ADO
    MSSQL_ADO_COMMAND_TIMEOUT = 30
    MSSQL_ADO_NAMED_CONNECTION = CubeManager
    MSSQL_ADO_QUERY_FEATURE_TYPES_FOR_MERGE_FILTERS = Yes
    SQL_STATEMENT:
      Select dbo.[Lookups].[Name], dbo.[Lookups].[AzureLookupFile], dbo.[Lookups].[SQLDWTableName], DATEPART(year,dbo.[Lookups].[AzureSourceUploaded]) as FileYear, DATEPART(month,dbo.[Lookups].[AzureSourceUploaded]) as FileMonth,DATEPART(day,dbo.[Lookups].[AzureSourceUploaded]) as FileDay, dbo.[LookupFields].Alias as FieldAlias, dbo.[LookupFields].FieldName, dbo.[LookupFields].FieldType, dbo.[LookupFields].IgnoreField
      from dbo.[Lookups]
      INNER JOIN dbo.[LookupFields] ON dbo.[Lookups].LookupId=dbo.[LookupFields].LookupId
      where dbo.[Lookups].LookupId = @Value(LookupId)
      ORDER BY  [LookupFields].FieldOrder
    RESULT -> DefineSQLDataType
    <REJECTED> -> Logger_2 [off]
    <REJECTED> -> AttributeCreator_2
Logger_2 [off]
    MAXCOORDS = 20
    MAXFEATS = 20
    MESSAGE = ERROR Could not get info on Lookup:
    LOGGED -> Terminator_2 [off]

Bookmark: Identify Microsoft SQL Data type
Note: Some fieldtypes define length or precision. We capture these so we can pass on the same ínformation to SQL Server
DefineSQLDataType
    FIELDTYPE = @Value(FieldType)
    -> AttributeCreator_4

Bookmark: BUILD TABLE NAME AND FIELD LIST IN ORDER TO CREATE PARAMETERS FOR DATABRICKS JOB
Note: Compile Field definitions / use the Alias for the fields
AttributeCreator_4
    ATTR_TABLE:
      SET_TO SQLFieldsDefinition = FME_CONDITIONAL:DEFAULT_VALUE'[@Value(FieldName)] @Value(SQLFieldType)  NULL'BOOL_OP;OR;COMPOSITE_TEST;1;TEST @Value(SQLFieldType) = text'[@Value(FieldName)] nvarchar(4000)'FME_NUM_CONDITIONS2___
      SET_TO SQLFieldNameList = [@Value(FieldName)]
      SET_TO DWFieldName = @ReplaceString(@Value(FieldName)," ","_")  @ReplaceString(@Value(SQLFieldType),"text","string")
    -> Aggregator
Aggregator
    ACCUM_ATTRS_NAME = Drop Incoming Attributes
    CONCAT_ATTRS = SQLFieldNameList DWFieldName SQLFieldsDefinition
    GROUP_BY = SQLDWTableName FileMonth AzureLookupFile FileYear Name FileDay LookupId
    MODE = Attributes Only
    ORDERED = No
    SEP = ",\n"
    AGGREGATE -> AttributeCreator_WARNING_2 [off]
    AGGREGATE -> AttributeCreator_5
Note: Create Table Name
AttributeCreator_5
    ATTR_TABLE:
      SET_TO ExternalTableName = L_@Value(Name)_External
      SET_TO DWTableName = L_@Value(Name)
      SET_TO DWTableName_Temp = L_@Value(Name)_Temp
    -> AttributeCreator_19
    -> GetLookupFilePath [AttributeSplitter_Input]
GetLookupFilePath
    AZURELOOKUPFILE = @Value(AzureLookupFile)
    AttributeCreator_10_Output -> CallProcessCubeJob [DatabrickAPICallerInput]

Bookmark: CREATE LOOKUP INTO DATABRICKS
CallProcessCubeJob: DatabricksAPICaller
    COMMAND = run-now
    DOMAIN = northeurope.azuredatabricks.net
    JOBID = 12
    METHOD = POST
    PARAMETER = "fields":"@Value(DWFieldName)","source_file":"@Value(AzureLookupFile)","target_table":"@Value(DWTableName)"
    TOKEN =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
    CallDatabricksJob_Output -> testRunJobError
Note: Check if the Job started correctly
testRunJobError: Tester
    BOOL_OP = OR
    COMPOSITE_TEST = 1 OR 2
    TEST_CLAUSE:
      TEST RunId ATTRIBUTE_IS_MISSING ""
      TEST @Value(RunId) = 0
    TEST_MODE = TEST
    PASSED -> AttributeCreator_17
    FAILED -> JobStartTimer
AttributeCreator_17
    ATTR_TABLE:
      SET_TO MessageString = Error running CreateLookupDataframe job: @Value(error)
      SET_TO TransformerPath = CREATE_LOOKUP_IN_TEAL\SQLExecutor_4
      SET_TO _error = Error running CreateLookupDataframe job: @Value(error)
    -> AttributeCreator_2_OUTPUT_-__AttributeCreator_ERROR
    -> StringReplacer
Note: In order to checkhow long it takes tp start the cluster
JobStartTimer: AttributeCreator
    ATTR_TABLE = SET_TO StartTime = @DateTimeNow()
    -> WaitUntilDatabtricksJobCompleted [CheckJobStatus_Input]
Note: Wait until Dtabricks completes or times out to start the cliuster
WaitUntilDatabtricksJobCompleted
    MINUTESTOTIMEOUT = 20
    RUNID = @Value(RunId)
    STARTTIME = @Value(StartTime)
    TestFilter_TERMINATED -> TestJobSuccess
    TestFilter_TERMINATED -> AttributeCreator_3
TestJobSuccess: Tester
    BOOL_OP = OR
    COMPOSITE_TEST = 1
    TEST_CLAUSE = TEST @Value(noError) = 1
    TEST_MODE = TEST
    PASSED -> SQLExecutor_3 [INITIATOR]
    FAILED -> AttributeCreator_16

Bookmark: Success in creating tables, Report success to database
SQLExecutor_3
    COMBINE_ATTRS = Keep Initiator Attributes if Conflict
    COMBINE_GEOM = Initiator Geometry Only
    DATASET = CubeManager
    FORMAT = MSSQL_ADO
    MSSQL_ADO_COMMAND_TIMEOUT = 30
    MSSQL_ADO_NAMED_CONNECTION = CubeManager
    MSSQL_ADO_QUERY_FEATURE_TYPES_FOR_MERGE_FILTERS = Yes
    SQL_STATEMENT:
      UPDATE dbo.Lookups
          set ErrorMessages = null,
              FMEJobIdSQLDWCreatedStatus=1,
              SQLDWTableName = '@Value(DWTableName)',
              SQLDWTableNameCreated = getdate()
      WHERE LookupId = @Value(LookupId)
    INITIATOR -> AttributeCreator_18
    <REJECTED> -> AttributeCreator_12
AttributeCreator_18
    ATTR_TABLE:
      SET_TO MessageString = Update field FMEJobIdSQLDWCreatedStatus
      SET_TO TransformerPath = SQLExecutor_3
    -> AttributeCreator_16_OUTPUT_-__AttributeCreator_INFO
AttributeCreator_12
    ATTR_TABLE:
      SET_TO MessageString = Error: @Value(_reader_error).
        WorkSpace: $(WORKSPACE_NAME)
        Transformer name:  SQLExecutor_3
      SET_TO TransformerPath = SQLExecutor_3
    -> AttributeCreator_2_OUTPUT_-__AttributeCreator_ERROR

Bookmark: Write Error message to DB and remove generated tables...
StringReplacer
    CASE = NO
    FIND_TEXT = '
    NO_MATCH = _FME_NO_OP_
    REGEXP = NO
    REPLACE_TEXT = "
    SRC_ATTRS = _error
    -> SQLExecutor_2 [INITIATOR]
SQLExecutor_2
    COMBINE_ATTRS = Result Attributes Only
    COMBINE_GEOM = Initiator Geometry Only
    DATASET = CubeManager
    FORMAT = MSSQL_ADO
    MSSQL_ADO_COMMAND_TIMEOUT = 30
    MSSQL_ADO_NAMED_CONNECTION = CubeManager
    MSSQL_ADO_QUERY_FEATURE_TYPES_FOR_MERGE_FILTERS = Yes
    SQL_STATEMENT:
      UPDATE dbo.Lookups
          set ErrorMessages = ISNULL(ErrorMessages,'') + ' @Value(_error)',
              FMEJobIdSQLDWCreatedStatus=0,
              SQLDWTableName = Null,
              SQLDWTableNameCreated = Null
      WHERE LookupId = @Value(LookupId)
    INITIATOR -> AttributeCreator_21
    <REJECTED> -> AttributeCreator_8
AttributeCreator_21
    ATTR_TABLE:
      SET_TO MessageString = @Value(_error)
      SET_TO TransformerPath = WriteError\SQLDosExecuter_5\Success
    -> AttributeCreator_16_OUTPUT_-__AttributeCreator_INFO
AttributeCreator_8
    ATTR_TABLE:
      SET_TO MessageString = Error: @Value(_reader_error).
        WorkSpace: $(WORKSPACE_NAME)
        Transformer name:  SQLExecutor_2
      SET_TO TransformerPath = WriteError\SQLExecutor_2
    -> AttributeCreator_2_OUTPUT_-__AttributeCreator_ERROR
AttributeKeeper [off]
    CREATE_BULK_MODE_FEATURES = No
    -> Terminator [off]
Terminator [off]
    MESSAGE = Failed executing sqlcmd.exe

Bookmark: Write logger
AttributeCreator_16_OUTPUT_-__AttributeCreator_INFO: Junction
    -> AttributeCreator_INFO
AttributeCreator_INFO
    ATTR_TABLE = SET_TO MessageType = INFO
    -> AttributeKeeper_2
AttributeCreator_WARNING_2: Junction
    -> AttributeCreator_WARNING
AttributeCreator_WARNING
    ATTR_TABLE = SET_TO MessageType = WARNING
    -> AttributeKeeper_2
AttributeCreator_2_OUTPUT_-__AttributeCreator_ERROR: Junction
    -> AttributeCreator_ERROR
AttributeCreator_ERROR
    ATTR_TABLE = SET_TO MessageType = ERROR
    -> AttributeKeeper_2
AttributeKeeper_2
    CREATE_BULK_MODE_FEATURES = No
    KEEP_ATTRS = TransformerPath,LookupId,MessageType,MessageString
    -> JediLogWritter
JediLogWritter
    FILEID = $(LookupId)
    MESSAGESTRING = @Value(MessageString)
    MESSAGETYPE = @Value(MessageType)
    OBJECTPROCESSED = Lookup
    SQLServerConn = CubeManager
    TRANSFORMERPATH = $(WORKSPACE_NAME)\STEP1: LOOKUP TO SQL DW\@Value(TransformerPath)
    -> Tester
Tester
    BOOL_OP = OR
    TEST_CLAUSE = TEST @Value(MessageType) = ERROR
    TEST_MODE = TEST
    PASSED -> Terminator_3
Terminator_3
    MESSAGE = Translation Terminated: @Value(MessageString)

FME custom transformer DefineSQLDataType

Parameters:
- FIELDTYPE =

Input (input)
    -> TestFilter
Note: How is the dimention configured? / For compatibility reasons we still translate the / fme_types but we slowly move towards microsoft sql types
TestFilter
    DEFAULT_VALUE = microsoft sql types
    TEST_LIST = BOOL_OP,OR,COMPOSITE_TEST,<Unused>,TEST_CLAUSE,"TEST @Value(FieldType) BEGINS_WITH fme_",fme types
    fme types -> StringSearcher
    microsoft sql types -> AttributeCreator_4
Note: If it doesn't start with "fme_" then / we assume that this is an Microsoft SQL Data type.
AttributeCreator_4
    ATTR_TABLE = SET_TO SQLFieldType = @Value(FieldType)
    -> StringReplacer
StringReplacer
    CASE = NO
    FIND_TEXT = n*varchar(\(\d+\))?
    NO_MATCH = _FME_NO_OP_
    REGEXP = YES
    REPLACE_TEXT = string
    SRC_ATTRS = SQLFieldType
    -> SqlTextToString
Note: Converts any sql text type to string type
SqlTextToString: AttributeValueMapper
    DIRECTION = Forward (Source To Destination)
    LUT = @FindString(@Value(SQLFieldType),varchar),string,@FindString(@Value(SQLFieldType),text),string,@Value(SQLFieldType),@Value(SQLFieldType)
    SRC = SQLFieldType
    VAL_ATTR = SQLFieldType
    -> Output (output)
Output (output)

Bookmark: Split FieltType from Details
Note: Some fieldtypes define length or precision. We capture these so we can pass on the same ínformation to SQL Server
StringSearcher
    CASE = no
    MATCHED_PARTS_ATTR = _TypeParts
    MATCHED_RESULT_ATTR = _first_match
    REGEXP = (fme_char|fme_varchar|fme_decimal)(\(\d{1,}\)|\(\d{1,},\d{1,}\))
    STRING_TO_SEARCH = @Value(FieldType)
    MATCHED -> AttributeCreator
    NOT_MATCHED -> AttributeCreator_2
AttributeCreator
    ATTR_TABLE:
      SET_TO FieldType = @Value(_TypeParts{0}.part)
      SET_TO _FieldTypeDetails = @Value(_TypeParts{1}.part)
    -> AttributeValueMapper
AttributeValueMapper
    DIRECTION = Forward (Source To Destination)
    LUT = fme_char,string,fme_varchar,string,fme_decimal,numeric
    SRC = FieldType
    VAL_ATTR = SQLFieldType
    -> AttributeCreator_3
Note: Compiles the full type / example varchar(20) / or numeric(29,8)
AttributeCreator_3
    ATTR_TABLE = SET_TO SQLFieldType = @Value(SQLFieldType)@Value(_FieldTypeDetails)
    -> AttributeRemover
AttributeCreator_2
    ATTR_TABLE = SET_TO _FieldTypeDetails
    -> AttributeValueMapper_2
AttributeValueMapper_2
    DIRECTION = Forward (Source To Destination)
    LUT = fme_int32,int,fme_int64,bigint,fme_uint64,bigint,fme_uint32,int,fme_int16,int,fme_uint16,int,fme_boolean,char(1) ,fme_int8,smallint,fme_uint8,smallint,fme_real32,float,fme_real64,float,fme_datetime,varchar(20),fme_date,varchar(20)
    SRC = FieldType
    VAL_ATTR = SQLFieldType
    -> AttributeRemover
AttributeRemover
    LIST_ATTRS = _TypeParts{}
    REMOVE_ATTRS = _FieldTypeDetails,_first_match
    -> Output (output)

FME custom transformer WaitUntilDatabtricksJobCompleted

Parameters:
- MINUTESTOTIMEOUT =
- RUNID =
- STARTTIME =

CheckJobStatus_Input (input)
    -> CheckRunStatus [DatabrickAPICallerInput]
CheckRunStatus: DatabricksAPICaller
    COMMAND = runs/get-output
    DOMAIN = northeurope.azuredatabricks.net
    METHOD = GET
    RUNID = @Value(RunId)
    TOKEN =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
    CallDatabricksJob_Output -> CurrentTimer
CurrentTimer: AttributeCreator
    ATTR_TABLE = SET_TO CurrentTime = @DateTimeNow()
    -> TestJobStatus
TestJobStatus: TestFilter
    DEFAULT_VALUE = <UNFILTERED>
    TEST_LIST = "BOOL_OP,OR,COMPOSITE_TEST,""""""1"""""",TEST_CLAUSE,TEST @Value(status) = TERMINATED",TERMINATED,"BOOL_OP,OR,COMPOSITE_TEST,""""""1"""""",TEST_CLAUSE,TEST @Value(status) = PENDING",PENDING,"BOOL_OP,OR,COMPOSITE_TEST,""""""1"""""",TEST_CLAUSE,TEST @Value(status) = RUNNING",RUNNING,"BOOL_OP,OR,COMPOSITE_TEST,""""""1"""""",TEST_CLAUSE,TEST @Value(status) = TERMINATING",TERMINATING
    TERMINATED -> TestFilter_TERMINATED (output)
    PENDING -> TimeOutStartingCluster
    RUNNING -> Decelerator
    TERMINATING -> Decelerator
    <UNFILTERED> -> Decelerator
TimeOutStartingCluster: Tester
    BOOL_OP = OR
    COMPOSITE_TEST = 1
    TEST_CLAUSE = TEST @Value(CurrentTime) >= @DateTimeAdd(@Value(StartTime), @DateTimeIntervalCreate(0,0,0,0,@Value(MinutesToTimeout),0) )
    TEST_MODE = TEST
    PASSED -> CancelRun [DatabrickAPICallerInput]
    FAILED -> Decelerator
CancelRun: DatabricksAPICaller
    COMMAND = runs/cancel
    DOMAIN = northeurope.azuredatabricks.net
    METHOD = POST
    RUNID = @Value(RunId)
    TOKEN =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
    CallDatabricksJob_Output -> SetErrorInDatabricksResult
SetErrorInDatabricksResult: AttributeCreator
    ATTR_TABLE:
      SET_TO error = Timeout starting cluster
      SET_TO noError = 0
      SET_TO num_records = 0
      SET_TO has_overlaps = 0
      SET_TO cmd = 0
    -> TestFilter_TERMINATED (output)
TestFilter_TERMINATED (output)
Decelerator
    DECEL_TYPE = Per Feature Delay
    DELAY = 15
    -> CheckJobStatus_Input (output)
CheckJobStatus_Input (output)

FME custom transformer DatabricksAPICaller
Custom Transformer to call Databricks API

Parameters:
- COMMAND =
- DOMAIN =
- JOBID =
- METHOD =
- PARAMETER =
- RUNID =
- TOKEN =

DatabrickAPICallerInput (input)
    -> ParameterFetcher
ParameterFetcher
    ATTR_LIST = _TOKEN $(TOKEN) _DOMAIN $(DOMAIN)
    -> CallDatabricksJob
Note: Call databricks API
CallDatabricksJob: PythonCaller
    NEW_ATTRIBUTES = RunId status result num_records has_overlaps error noError cmd
    PYTHONSOURCE:
      import fme
      import fmeobjects
      import json
      import base64
      import requests
      import re


      # Template Function interface:
      # When using this function, make sure its name is set as the value of
      # the 'Class or Function to Process Features' transformer parameter
      def dbfs_rpc(action, body,TOKEN,BASE_URL):
        """ A helper function to make the API request, request/response is encoded/decoded as JSON """
        response = requests.post(
          BASE_URL + action,
          headers={"Authorization":"Bearer " +str(TOKEN) },
          json=body
        )
        return response.json()

      def dbfs_get_rpc(action, body,TOKEN,BASE_URL):
        """ A helper function to make the API request, request/response is encoded/decoded as JSON """
        response = requests.get(
          BASE_URL + action,
          headers={"Authorization":"Bearer " + str(TOKEN) },
          params= body
        )
        return response.json()



      def processFeature(feature):
          pass

      # Template Class Interface:
      # When using this class, make sure its name is set as the value of
      # the 'Class or Function to Process Features' transformer parameter
      class FeatureProcessor(object):
          def __init__(self):
              pass
          def input(self,feature):
              runId= 0
              status=""
              result=""
              num_records =0
              has_overlaps =0
              error= ""
              noError=0
              cmd =0
              try:

                  raw_data = {}
                  if feature.getAttribute('RunId'):
                      raw_data['run_id']= str(feature.getAttribute('RunId'))
                  if feature.getAttribute('JobId'):
                      raw_data['job_id']= feature.getAttribute('JobId')

                  if feature.getAttribute('Parameter'):
                      paramTxt = "{" + str(feature.getAttribute('Parameter')) + "}"
                      formatedParam = paramTxt.replace("\n"," ").replace("\t", " ").replace("  "," ")
                      parameter = json.loads(formatedParam)
                      raw_data['notebook_params'] = parameter

                  DOMAIN = str(feature.getAttribute('_DOMAIN'))
                  TOKEN = str(feature.getAttribute('_TOKEN'))
                  BASE_URL = 'https://%s/api/2.0/jobs/' % (DOMAIN)


                  if feature.getAttribute('Method') == 'POST':
                      handle = dbfs_rpc(feature.getAttribute('Command'), raw_data,TOKEN, BASE_URL)
                  else:
                      handle = dbfs_get_rpc(feature.getAttribute('Command'), raw_data,TOKEN, BASE_URL)
                  noError=1

                  if ('run_id' in handle):
                      runId= handle['run_id']
                  else:
                      runId= str(feature.getAttribute('RunId'))

                  if 'metadata' in handle:
                      if 'state' in handle['metadata']:
                          if 'life_cycle_state' in handle['metadata']['state']:
                              status = handle['metadata']['state']['life_cycle_state']
                          if 'result_state' in handle['metadata']['state']:
                              result = handle['metadata']['state']['result_state']

                      if status == 'TERMINATED' : # and 'notebook_output' in handle:
                          if 'result' in  handle['notebook_output']:
                              output = handle['notebook_output']['result'].replace('\n', ' ').replace('\r', '').replace('\t', '').replace("  ","")
                              res = json.loads(output)
                              noError = res['status']
                              cmd = res['cmd']
                              error = res['error']
                              if 'num_records' in res:
                                  num_records = res['num_records']
                              if 'has_overlaps' in res:
                                  has_overlaps = res['has_overlaps']


              except Exception as err:
                  print("DATABRICKS ERRROR")
                  print("error:" + str(err))
                  feature.setAttribute("RunId",0)
                  feature.setAttribute("error",str(err))
                  feature.setAttribute("noError",0)

              feature.setAttribute("RunId",runId)
              feature.setAttribute("status",status)
              feature.setAttribute("result",result)
              feature.setAttribute("num_records",num_records)
              feature.setAttribute("has_overlaps",has_overlaps)
              feature.setAttribute("error",error)
              feature.setAttribute("noError",noError)
              feature.setAttribute("cmd",cmd)
              self.pyoutput(feature)

          def close(self):
              pass
    PYTHONSYMBOL = FeatureProcessor
    -> CallDatabricksJob_Output (output)
CallDatabricksJob_Output (output)

FME custom transformer GetLookupFilePath

Parameters:
- AZURELOOKUPFILE =

AttributeSplitter_Input (input)
    -> AttributeSplitter
Note: Split path with / separator
AttributeSplitter
    ATTR_NAME = AzureLookupFile
    DELIMITER = /
    DROP_EMPTY_PARTS = No
    LIST_NAME = _list
    TRIM_OPTION = Both
    -> AttributeCreator_10
Note: Build the string with all the path but the last one
AttributeCreator_10
    ATTR_TABLE = SET_TO AzureLookupFile = @Value(_list{0})/@Value(_list{1})
    -> AttributeCreator_10_Output (output)
AttributeCreator_10_Output (output)
