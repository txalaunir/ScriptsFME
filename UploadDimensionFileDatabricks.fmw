FME workspace UploadDimensionFileDatabricks.fmw
Title: Import external dimension file
Description: Upload dimension file generated outside the integrated assessment accounting infrastructure. These files must contain the field GridNum that follows the grid coding system.
Usage: If you have a pre-generated dimension file (.csv) that includes the GridCode as attribute. Zip this single file and upload it using this workspace to inlcude it inside the infrastructure.
History: 14/07/2016,Jan Bliki,Initial creation

Parameters:
- FileId = 6

SQLCreator
    DATASET = CubeManager
    EXPOSED_ATTRIBUTE_LIST = CubeDimensionId,FileId,SourceFile,CubeShortName,GridTypesShortName,SourceFileReceived
    FORMAT = MSSQL_ADO
    MSSQL_ADO_COMMAND_TIMEOUT = 30
    MSSQL_ADO_NAMED_CONNECTION = CubeManager
    MSSQL_ADO_QUERY_FEATURE_TYPES_FOR_MERGE_FILTERS = Yes
    SQL_STATEMENT:
      select  CubeDimensions.CubeDimensionId,
              GridTypes.name as GridTypesShortName,
              CubeDimensions.Name as CubeShortName,
              Files.FileId,
              Files.SourceFile,
              Files.SourceFileReceived
      from CubeDimensions
      inner join Files on CubeDimensions.CubeDimensionId = Files.CubeDimensionId
      inner join GridTypes on GridTypes.GridTypeId = Cubedimensions.GridTypeId
      where FileId = $(FileId)
      --and FmeConversionProcess = '$(WORKSPACE_NAME)'
    RESULT -> AttributeCreator_13
    <REJECTED> -> AttributeCreator_10
Note: Find Dimension temp path
SQLExecutor
    COMBINE_ATTRS = Keep Initiator Attributes if Conflict
    COMBINE_GEOM = Initiator Geometry Only
    DATASET = CubeManager
    EXPOSED_ATTRIBUTE_LIST = __TempDimensionLocationPath
    FORMAT = MSSQL_ADO
    MSSQL_ADO_COMMAND_TIMEOUT = 30
    MSSQL_ADO_NAMED_CONNECTION = CubeManager
    MSSQL_ADO_QUERY_FEATURE_TYPES_FOR_MERGE_FILTERS = Yes
    SQL_STATEMENT:
      select AttributeValue as __TempDimensionLocationPath
      from dbo.GeneralInfo
      where AttributeName = 'DimensionTempLocation'
    RESULT -> DateFormatter
    <REJECTED> -> AttributeCreator_9
DateFormatter
    DATE_ATTR = SourceFileReceived
    FMT = %Y_%m_%d
    INVALID_DATE_VALUE = _FME_NO_OP_
    SRCFMT = %Y%m%d%H%M%S.000
    -> VariableSetter
VariableSetter
    SCOPE = Global
    VALUE = @Value(CubeShortName)_@Value(GridTypesShortName)_@Value(SourceFileReceived).csv
    VARNAME = originalFileName
    -> ValidateZipContent
FeatureMerger
    ATTR_ACCUM_MODE = Merge Supplier
    ATTR_CONFLICT_RES = Use Requestor
    IGNORE_NULLS = No
    JOIN_KEYS = 1 1 AUTO
    MERGE_TYPE = Attributes Only
    PROCESS_DUPS = No
    REJECT_NULL_MISSING_KEYS = No
    SUPPLIERS_FIRST = No
    MERGED -> Store_File_Info [INITIATOR]
    MERGED -> AttributeCreator_5
AttributeCreator_5
    ATTR_TABLE:
      SET_TO MessageString = FeatureMerger passed by Merged.
      SET_TO TransformerPath = FeatureMerger/Merged
    -> TYPO_INFO
Note: Set dimensionprocess status to one
Store_File_Info: SQLExecutor
    COMBINE_ATTRS = Result Attributes Only
    COMBINE_GEOM = Initiator Geometry Only
    DATASET = CubeManager
    FORMAT = MSSQL_ADO
    MSSQL_ADO_COMMAND_TIMEOUT = 30
    MSSQL_ADO_NAMED_CONNECTION = CubeManager
    MSSQL_ADO_QUERY_FEATURE_TYPES_FOR_MERGE_FILTERS = Yes
    SQL_STATEMENT:
      Update dbo.Files
          set [DimensionFile] = '@Value(__TempDimensionLocationPath)',
              [DimensionFileCreated]=getdate(),
              [FMEJobIdDimensionProcessStatus]=1,
              ErrorMessages = Null
      where FileId = @Value(FileId)
    INITIATOR -> TYPO_INFO
    <REJECTED> -> TYPE_ERROR
TYPO_INFO: AttributeCreator
    ATTR_TABLE = SET_TO MessageType = INFO
    -> AttributeKeeper_2
AttributeKeeper_2
    CREATE_BULK_MODE_FEATURES = No
    KEEP_ATTRS = MessageString,MessageType,TransformerPath,FileId
    -> JediLogWritter
AttributeCreator_Error_3
    ATTR_TABLE = SET_TO MessageString = Could not extract file (@Value(_OriginalDimensionFile)) from .zip (@Value(sourceFile))
    -> AttributeCreator_Error_3_OUTPUT_-__TYPE_ERROR
AttributeCreator_8
    ATTR_TABLE:
      SET_TO MessageString = Transformer: SQLExecutor_Accespted
        Error: @Value(_reader_error)
      SET_TO TransformerPath = SQLExecutor_Accespted
    -> AttributeCreator_Error_3_OUTPUT_-__TYPE_ERROR
AttributeCreator_6
    ATTR_TABLE:
      SET_TO MessageString = Transformer: SQLExe_Delete
        Error: @Value(_reader_error)
      SET_TO TransformerPath = SQLExe_Delete
    -> AttributeCreator_Error_3_OUTPUT_-__TYPE_ERROR
AttributeCreator_7
    ATTR_TABLE:
      SET_TO MessageString = Transformer: SQLExe_InsertUpdate
        Error: @Value(_reader_error)
      SET_TO TransformerPath = SQLExe_InsertUpdate
    -> AttributeCreator_Error_3_OUTPUT_-__TYPE_ERROR
AttributeCreator_3
    ATTR_TABLE:
      SET_TO MessageString = Transformer: SQLExecutor_Error
        Error: @Value(_reader_error)
      SET_TO TransformerPath = SQLExecutor_Error
    -> AttributeCreator_Error_3_OUTPUT_-__TYPE_ERROR
AttributeCreator_Error_3_OUTPUT_-__TYPE_ERROR: Junction
    -> TYPE_ERROR
AttributeCreator_9
    ATTR_TABLE:
      SET_TO MessageString = Transformer: SQLExecutor
        Error: @Value(_reader_error)
      SET_TO TransformerPath = SQLExecutor
    -> TYPE_ERROR
AttributeCreator_11
    ATTR_TABLE:
      SET_TO MessageString = Transformer: STore_File_Info_2
        Error: @Value(_reader_error)
      SET_TO TransformerPath = Store_File_Info_2
    -> TYPE_ERROR
AttributeCreator_10
    ATTR_TABLE:
      SET_TO MessageString = Transformer: SQLCreator
        Error: @Value(_reader_error)
      SET_TO TransformerPath = SQLCreator
    -> TYPE_ERROR
TYPE_ERROR: AttributeCreator
    ATTR_TABLE = SET_TO MessageType = ERROR
    -> AttributeKeeper
AttributeKeeper
    CREATE_BULK_MODE_FEATURES = No
    KEEP_ATTRS = MessageString,MessageType,TransformerPath,FileId
    -> JediLogWritter
JediLogWritter
    FILEID = $(FileId)
    MESSAGESTRING = @Value(MessageString)
    MESSAGETYPE = @Value(MessageType)
    OBJECTPROCESSED = Dimension
    SQLServerConn = CubeManager
    TRANSFORMERPATH = $(WORKSPACE_NAME)\STEP1:SOURCE FORMAT TO GRID\@Value(TransformerPath)
    -> Tester_2
Tester_2
    BOOL_OP = OR
    TEST_CLAUSE = TEST @Value(MessageType) = ERROR
    TEST_MODE = Automatic
    PASSED -> Terminator_2
Terminator_2
    MESSAGE = Translation Terminated: @Value(MessageString)

Bookmark: Tell DB we are executing the job
Note: Reset the database and provide the job_id so log information can be found easily.
AttributeCreator_13
    ATTR_TABLE = SET_TO _FME_JOB_ID = FME_CONDITIONAL:DEFAULT_VALUE'$(FME_JOB_ID)'BOOL_OP;AND;COMPOSITE_TEST;<Unused>;TEST $(FME_JOB_ID) ATTRIBUTE_IS_MISSING _FME_BLANK_STRING_;TEST $(FME_JOB_ID) NOT_ATTRIBUTE_HAS_VALUE _FME_BLANK_STRING_'-1'FME_NUM_CONDITIONS2___
    -> Store_File_Info_2 [INITIATOR]
Store_File_Info_2: SQLExecutor
    COMBINE_ATTRS = Result Attributes Only
    COMBINE_GEOM = Initiator Geometry Only
    DATASET = CubeManager
    FORMAT = MSSQL_ADO
    MSSQL_ADO_COMMAND_TIMEOUT = 30
    MSSQL_ADO_NAMED_CONNECTION = CubeManager
    MSSQL_ADO_QUERY_FEATURE_TYPES_FOR_MERGE_FILTERS = Yes
    SQL_STATEMENT:
      Update dbo.Files
          set [FMEJobIdDimensionProcess]=@Value(_FME_JOB_ID)
      where FileId = @Value(FileId)
    INITIATOR -> SQLExecutor [INITIATOR]
    <REJECTED> -> AttributeCreator_11

Bookmark: Find out if the content is correct.
ValidateZipContent
    FILEID = @Value(FileId)
    SOURCEFILE = @Value(SourceFile)
    Continue -> SQLExecutor_Accepted [INITIATOR]
    Fields -> SQLExe_InsertUpdate [INITIATOR]
    Error -> SQLExecutor_Error [INITIATOR]
SQLExecutor_Accepted
    COMBINE_ATTRS = Result Attributes Only
    COMBINE_GEOM = Initiator Geometry Only
    DATASET = CubeManager
    FORMAT = MSSQL_ADO
    MSSQL_ADO_COMMAND_TIMEOUT = 30
    MSSQL_ADO_NAMED_CONNECTION = CubeManager
    MSSQL_ADO_QUERY_FEATURE_TYPES_FOR_MERGE_FILTERS = Yes
    SQL_STATEMENT:
      Update dbo.Files
          set Validated = 1,
              FMEJobIdValidator=@Value(FMEJobIdValidator)
      where FileId = @Value(FileId)
    INITIATOR -> TempPathnameCreator
    <REJECTED> -> AttributeCreator_8
SQLExe_InsertUpdate: SQLExecutor
    COMBINE_ATTRS = Result Attributes Only
    COMBINE_GEOM = Initiator Geometry Only
    DATASET = CubeManager
    FORMAT = MSSQL_ADO
    MSSQL_ADO_COMMAND_TIMEOUT = 30
    MSSQL_ADO_NAMED_CONNECTION = CubeManager
    MSSQL_ADO_QUERY_FEATURE_TYPES_FOR_MERGE_FILTERS = Yes
    SQL_STATEMENT = exec dbo.InsertFieldIntoDimensionFields @Value(FileId),'@Value(FieldName)','@Value(Alias)','@Value(FieldType)',0,'@Value(Title)','@Value(Description)'
    INITIATOR -> Aggregator
    <REJECTED> -> AttributeCreator_7
Aggregator
    ACCUM_ATTRS_NAME = Get Attributes From One Representative Feature
    AGGREGATE_TYPE = Homogeneous Collection (If Possible)
    CONCAT_ATTRS = FieldName
    MODE = Geometry - Assemble One Level
    ORDERED = No
    SEP = ','
    AGGREGATE -> SQL_Exe_Delete [INITIATOR]
SQL_Exe_Delete: SQLExecutor
    COMBINE_ATTRS = Result Attributes Only
    COMBINE_GEOM = Initiator Geometry Only
    DATASET = CubeManager
    FORMAT = MSSQL_ADO
    MSSQL_ADO_COMMAND_TIMEOUT = 30
    MSSQL_ADO_NAMED_CONNECTION = CubeManager
    MSSQL_ADO_QUERY_FEATURE_TYPES_FOR_MERGE_FILTERS = Yes
    SQL_STATEMENT:
      delete fields
          where fileId = @Value(FileId)
              and FieldName not in ('@Value(FieldName)')
    <REJECTED> -> AttributeCreator_6
SQLExecutor_Error
    COMBINE_ATTRS = Result Attributes Only
    COMBINE_GEOM = Initiator Geometry Only
    DATASET = CubeManager
    FORMAT = MSSQL_ADO
    MSSQL_ADO_COMMAND_TIMEOUT = 30
    MSSQL_ADO_NAMED_CONNECTION = CubeManager
    MSSQL_ADO_QUERY_FEATURE_TYPES_FOR_MERGE_FILTERS = Yes
    SQL_STATEMENT:
      Update dbo.Files
          set Validated = 0,
              ErrorMessages = '@Value(ErrorMessage)',
              FMEJobIdValidator=@Value(FMEJobIdValidator)
      where FileId = @Value(FileId)
    <REJECTED> -> AttributeCreator_3

Bookmark: EXTRACT FILE FROM ZIP
TempPathnameCreator
    PATHNAME_ATTR = __TempPathName
    -> ExtractFileFromZip
ExtractFileFromZip
    DESTINATIONFOLDER = @Value(__TempPathName)
    SOURCEFILE = @Value(_OriginalDimensionFile)
    ZIPSOURCEFILE = @Value(SourceFile)
    SUCCESS -> VariableRetriever_2
    FAILED -> Error_zip_extraction [off]
    FAILED -> AttributeCreator_Error_3
VariableRetriever_2
    SCOPE = Global
    VALUE_ATTR = __originalFileName
    VARNAME = originalFileName
    -> FilenamePartExtractor
FilenamePartExtractor
    ROOTNAME_ATTR = fme_feature_basename
    SRC_ATTR = @Value(__originalFileName)
    -> AttributeCreator
AttributeCreator
    ATTR_TABLE = SET_TO __TempDimensionLocationPath = @Value(__TempDimensionLocationPath)\@Value(fme_feature_basename)
    -> StringReplacer
StringReplacer
    CASE = NO
    FIND_TEXT = \\
    NO_MATCH = _FME_NO_OP_
    REGEXP = YES
    REPLACE_TEXT = /
    SRC_ATTRS = __TempDimensionLocationPath
    -> FeatureMerger [SUPPLIER]
    -> CreateFolder [FileName]
Error_zip_extraction: Terminator [off]
    MESSAGE = Could not extract file (@Value(_OriginalDimensionFile)) from .zip (@Value(sourceFile))

Bookmark: SPLIT FILE INTO HEADER AND BODY
Note: The first line (Field names) are split from the body. The body text is compressed (.gz) and all stored in a single Folder
CreateFolder: FileSystemDeleteMoveCopyExist_2
    Action = MKDIR
    FILEINPUT = @Value(__TempDimensionLocationPath)
    Success -> FeatureReader [INITIATOR]
    Success -> AttributeCreator_2
    NotFound -> Terminator [off]
    NotFound -> AttributeCreator_CreteFolder
    Failed -> Terminator [off]
    Failed -> AttributeCreator_CreteFolder
AttributeCreator_2
    ATTR_TABLE:
      SET_TO MessageString = Folder create successful
      SET_TO TransformerPath = SPLIT FILE INTO HEADER AND BODY\CreateFolder
    -> TYPO_INFO
FeatureReader
    ATTR_ACCUM_MODE = Merge Initiator and Result
    ATTR_CONFLICT_RES = Use Result
    COMBINE_GEOM = Use Result
    DATASET = @Value(__TempPathName)/@Value(_OriginalDimensionFile)
    FORMAT = TEXTLINE
    OUTPUT_FEATURES_DISPLAY = Schema and Data Features
    TEXTLINE_READ_BOTTOM_UP = No
    TEXTLINE_READ_WHOLE_FILE_AT_ONCE = NO
    TEXTLINE_SKIP_FOOTER = 0
    TEXTLINE_SKIP_LINES = 0
    <OTHER> -> Sampler
    <OTHER> -> AttributeCreator_4
    <REJECTED> -> FeatureReader__REJECTED__-__TYPE_ERROR
AttributeCreator_4
    ATTR_TABLE:
      SET_TO MessageString = The first line (Field names) are split from the body. The body text is compressed (.gz) and all stored in a single Folder
      SET_TO TransformerPath = SPLIT FILE INTO HEADER AND BODY\FeatureReader
    -> FeatureReader__OTHER__-__TYPO_INFO
FeatureReader__OTHER__-__TYPO_INFO: Junction
    -> TYPO_INFO
Sampler
    RATE = 1
    SAMPLE_MODE = No
    SAMPLE_TYPE_LONG = First N Features
    SAMPLED -> FeatureWriter_2 [text_line]
    NOT_SAMPLED -> FeatureWriter [text_line]
FeatureWriter_2
    DATASET = @Value(__TempDimensionLocationPath)/@Value(__originalFileName).fieldnames
    DATASET_ATTR = _dataset
    FEATURE_TYPE_LIST_ATTR = _feature_type
    FORMAT = TEXTLINE
    TEXTLINE_DESTINATION_DATASETTYPE_VALIDATION = Yes
    TEXTLINE_ENCODING = utf-8
    TEXTLINE_END_OF_LINE = System
    TEXTLINE_MIME_TYPE = text/plain
    TEXTLINE_OVERWRITE_FILE = YES
    TEXTLINE_WRITE_LAST_EOL = NO
    TEXTLINE_WRITE_UTF8_BOM = NO
    TOTAL_FEATURES_WRITTEN_ATTR = _total_features_written
    WRITER_DIRECTIVES = ENCODING,utf-8,END_OF_LINE,System,DESTINATION_DATASETTYPE_VALIDATION,Yes,OVERWRITE_FILE,YES,WRITE_LAST_EOL,NO,WRITE_UTF8_BOM,NO,MIME_TYPE,text/plain
FeatureWriter
    DATASET = @Value(__TempDimensionLocationPath)/@Value(__originalFileName)
    DATASET_ATTR = _dataset
    FEATURE_TYPE_LIST_ATTR = _feature_type
    FORMAT = TEXTLINE
    TEXTLINE_COORDINATE_SYSTEM_GRANULARITY = FEATURE
    TEXTLINE_DESTINATION_DATASETTYPE_VALIDATION = Yes
    TEXTLINE_ENCODING = SYSTEM
    TEXTLINE_END_OF_LINE = System
    TEXTLINE_MIME_TYPE = text/plain
    TEXTLINE_OVERWRITE_FILE = YES
    TEXTLINE_WRITE_LAST_EOL = YES
    TEXTLINE_WRITE_UTF8_BOM = YES
    TOTAL_FEATURES_WRITTEN_ATTR = _total_features_written
    WRITER_DIRECTIVES = ENCODING,SYSTEM,END_OF_LINE,System,DESTINATION_DATASETTYPE_VALIDATION,Yes,OVERWRITE_FILE,YES,WRITE_LAST_EOL,YES,WRITE_UTF8_BOM,YES,MIME_TYPE,text/plain
    SUMMARY -> FeatureMerger [REQUESTOR]
FeatureReader__REJECTED__-__TYPE_ERROR: Junction
    -> TYPE_ERROR
Terminator [off]
    MESSAGE = Could not make folder "@Value(__TempDimensionLocationPath)"
AttributeCreator_CreteFolder
    ATTR_TABLE:
      SET_TO MessageString = Folder not found
      SET_TO TransformerPath = SPLIT FILE INTO HEADER AND BODY - CreateFolder
    -> AttributeCreator_Error_2_OUTPUT_-__TYPE_ERROR
AttributeCreator_Error_2_OUTPUT_-__TYPE_ERROR: Junction
    -> TYPE_ERROR

FME custom transformer ExtractFileFromZip_3

Parameters:
- ZIPSOURCEFILE = @Value(zipSourceFile)   # Zipsourcefile
- SOURCEFILE = @Value(sourceFile)   # Sourcefile
- DESTINATIONFOLDER = @Value(destinationFolder)   # Destinationfolder

INPUT (input)
    -> CreateOutputFolder [FileName]
CreateOutputFolder: FileSystemDeleteMoveCopyExist
    Action = EXIST
    FILEINPUT = @Value(destinationFolder)
    Success -> unZipPython
unZipPython: PythonCaller
    NEW_ATTRIBUTES = _status
    PYTHONSOURCE:
      import fmeobjects
      import zipfile,os.path
      # Template Function interface:
      def processFeature(feature):
          pass

      # Template Class Interface:
      class FeatureProcessor(object):
          #
          # Extracts one file
          #
          def unzipOneFile(self,source_filename,filename,dest_dir):
              zfile = zipfile.ZipFile(source_filename)
              zfile.extract(filename,dest_dir)

          def __init__(self):
              pass
          def input(self,feature):
              source_filename = feature.getAttribute("zipSourceFile")
              filename = feature.getAttribute("sourceFile")
              dest_dir = feature.getAttribute("destinationFolder")
              #
              status = "success"
              # execute unzip
              #self.unzipOneFile(source_filename,filename,dest_dir)
              try:
                  self.unzipOneFile(source_filename,filename,dest_dir)
              except Exception:
                  status="failed"
                  pass
              # set if successfull
              feature.setAttribute("_status",status)
              self.pyoutput(feature)
          def close(self):
              pass
    PYTHONSYMBOL = FeatureProcessor
    -> TestFilter
TestFilter
    DEFAULT_VALUE = FAILED
    TEST_LIST = BOOL_OP,OR,COMPOSITE_TEST,<Unused>,TEST_CLAUSE,"TEST @Value(_status) = success",SUCCESS
    SUCCESS -> SUCCESS (output)
    FAILED -> RemoveFolder [FileName]
    FAILED -> Failed
SUCCESS (output)
RemoveFolder: FileSystemDeleteMoveCopyExist
    Action = EXIST
    FILEINPUT = @Value(destinationFolder)
    Success -> FAILED (output)
    Failed -> FAILED (output)
FAILED (output)
Failed: Inspector [off]

FME custom transformer FileSystemDeleteMoveCopyExist
This transformer can "move","copy","delete" files. Can as well check if a file "exist" and create or delete folders.
action:The action you like to perform. 
    fileInput: provide the input file path.
    fileOutput: provide the output file path. (Is not used when you delete or test the existance of a file)

Parameters:
- Action = EXIST
- FILEINPUT = @Value(fileInput)   # Fileinput
- FILEOUTPUT =   # Fileoutput

FileName (input)
    -> ParameterFetcher
ParameterFetcher
    ATTR_LIST = action {$(Action)} fileInput {$(FILEINPUT)} fileOutput {$(FILEOUTPUT)}
    -> PythonCaller
PythonCaller
    NEW_ATTRIBUTES = "_status "
    PYTHONSOURCE:
      import fmeobjects
      # Template Function interface:
      def processFeature(feature):
          pass

      # Template Class Interface:
      class FeatureProcessor(object):
          def __init__(self):
              pass
          def input(self,feature):
              import os,shutil

              # define and get parameters
              self._status=''
              self._fileInput = feature.getAttribute('fileInput')
              self._fileOutput = feature.getAttribute('fileOutput')
              self._action = feature.getAttribute('action')

              # When action is "delete"
              if (self._action.upper() == "DELETE"):
                  if os.path.exists(self._fileInput):
                      os.remove(self._fileInput)
                      self._status='deleted'
                  else:
                      self._status='notexist:' + self._fileInput

              # When action is "delete folder"
              if (self._action.upper() == "RMDIR"):
                  if os.path.exists(self._fileInput):
                      shutil.rmtree(self._fileInput)
                      self._status='deleted'
                  else:
                      self._status='notexist:' + self._fileInput

              # When action is "copy"
              if (self._action.upper() == "COPY"):
                  if os.path.exists(self._fileInput):
                      shutil.copy(self._fileInput,self._fileOutput)
                      self._status='copied'
                  else:
                      self._status='notexist:' + self._fileInput

              # When action is "move"
              if (self._action.upper() == "MOVE"):
                  if os.path.exists(self._fileInput):
                      shutil.move(self._fileInput,self._fileOutput)
                      self._status='moved'
                  else:
                      self._status='notexist:' + self._fileInput

              # When action is " mkdir"
              if (self._action.upper() == "MKDIR"):
                  if os.path.exists(self._fileInput):
                      self._status='created'
                  else:
                      os.makedirs(self._fileInput)
                      self._status='created'

              # When action is "exist"
              if (self._action.upper() == "EXIST"):
                  if os.path.exists(self._fileInput):
                      self._status='exist'
                  else:
                      self._status='notexist:' + self._fileInput

              feature.setAttribute('_status',self._status)
              self.pyoutput(feature)
          def close(self):
              pass
    PYTHONSYMBOL = FeatureProcessor
    -> TestFilter
TestFilter
    DEFAULT_VALUE = Failed
    TEST_LIST:
      BOOL_OP,OR,COMPOSITE_TEST,<Unused>,TEST_CLAUSE,"TEST @Value(_status) = deleted
      TEST @Value(_status) = copied
      TEST @Value(_status) = moved
      TEST @Value(_status) = exist
      TEST @Value(_status) = created",Success,BOOL_OP,OR,COMPOSITE_TEST,<Unused>,TEST_CLAUSE,"TEST @Value(_status) BEGINS_WITH notexist:",DoesNotExist
    Success -> Success (output)
    DoesNotExist -> NotFound (output)
    Failed -> Failed (output)
Success (output)
NotFound (output)
Failed (output)

FME custom transformer ValidateZipContent

Parameters:
- SOURCEFILE = @Value(SourceFile)   # SourceFile
- FILEID = @Value(FileId)   # FileId

Input (input)
    -> AttributeCreator_4
AttributeCreator_3
    ATTR_TABLE = SET_TO fme_feature_type = @Value(SourceFile)\@Value(zipFileName)
    -> FilenamePartExtractor_2
    -> FeatureReader [INITIATOR]
FilenamePartExtractor_2
    FULLNAME_ATTR = _OriginalDimensionFile
    SRC_ATTR = @Value(fme_feature_type)
    -> Continue (output)
Continue (output)
Note: StringReplacer : Input
AttributeCreator_OUTPUT: Junction
    -> StringReplacer_2
Note: AttributeCreator : Output
StringReplacer_2: Junction
    -> StringReplacer
StringReplacer
    CASE = NO
    FIND_TEXT = '
    NO_MATCH = _FME_NO_OP_
    REGEXP = NO
    REPLACE_TEXT = ''
    SRC_ATTRS = ErrorMessage
    -> Error (output)
Error (output)

Bookmark: Get JobId
AttributeCreator_4
    ATTR_TABLE = SET_TO FMEJobIdValidator = FME_CONDITIONAL:DEFAULT_VALUE'-1'BOOL_OP;OR;COMPOSITE_TEST;<Unused>;TEST $(FME_JOB_ID) ATTRIBUTE_HAS_VALUE _FME_BLANK_STRING_'$(FME_JOB_ID)'FME_NUM_CONDITIONS2___
    -> FilenamePartExtractor

Bookmark: Check File extension
FilenamePartExtractor
    EXTENSION_ATTR = SourceFile_extension
    SRC_ATTR = @Value(SourceFile)
    -> TestFilter
TestFilter
    DEFAULT_VALUE = OtherFormat
    TEST_LIST = BOOL_OP,OR,COMPOSITE_TEST,<Unused>,TEST_CLAUSE,"TEST @LowerCase(@Value(SourceFile_extension)) = zip",IsAZipFile
    IsAZipFile -> FileSystemDeleteMoveCopyExist [FileName]
    OtherFormat -> AttributeCreator
AttributeCreator
    ATTR_TABLE = SET_TO ErrorMessage = File must be a .zip that contains a .CSV file only.
    -> AttributeCreator_OUTPUT

Bookmark: Check if the file exists
FileSystemDeleteMoveCopyExist: FileSystemDeleteMoveCopyExist_2
    Action = EXIST
    FILEINPUT = @Value(SourceFile)
    Success -> getMetaDataFromZip [InputZip]
    NotFound -> AttributeCreator_6
AttributeCreator_6
    ATTR_TABLE = SET_TO ErrorMessage = Source file (@Value(SourceFile))  can't be found or isn't accessible by the FME server.
    -> AttributeCreator_OUTPUT

Bookmark: Read zip and find .tiff and .legend
getMetaDataFromZip
    inputZipFile = @Value(SourceFile)
    scanZipInZip = yes
    -> TestFilter_2
    -> StringCaseChanger

Bookmark: Check if .shp exists
TestFilter_2
    DEFAULT_VALUE = File is missing
    TEST_LIST = BOOL_OP,AND,COMPOSITE_TEST,<Unused>,TEST_CLAUSE,"TEST @LowerCase(@Value(fileExtension)) CONTAINS csv",CSV-File
    CSV-File -> AttributeCreator_3
StringCaseChanger
    ATTRCHOICE = Selected Attributes
    ATTRLIST = fileExtension
    CHANGE_TYPE = lowercase
    -> Aggregator
Aggregator
    ACCUM_ATTRS_NAME = Get Attributes From One Representative Feature
    AGGREGATE_TYPE = Homogeneous Collection (If Possible)
    CONCAT_ATTRS = fileExtension
    MODE = Geometry - Assemble One Level
    ORDERED = No
    SEP = ,
    AGGREGATE -> TestFilter_3
TestFilter_3
    DEFAULT_VALUE = DidNotFindShp
    TEST_LIST = BOOL_OP,OR,COMPOSITE_TEST,<Unused>,TEST_CLAUSE,"TEST csv IN @Value(fileExtension)",FoundShp
    DidNotFindShp -> AttributeCreator_2
AttributeCreator_2
    ATTR_TABLE = SET_TO ErrorMessage = CSV file is not found, please provide a CSV file inside the .zip.
    -> StringReplacer

Bookmark: Create fields for image
FeatureReader
    ATTR_ACCUM_MODE = Only Use Result
    COMBINE_GEOM = Use Result
    CSV_SCAN_MAX_FEATURES = 0
    CSV__ALLOW_SPACES_IN_COLUMN_NAMES = yes
    CSV__DUPLICATE_DELIMS = no
    CSV__FIELD_NAMES_AFTER_HEADER = no
    CSV__FILTER_TABLE_CONFIG = "NOT_OK_IF_INVALID%NO_LABEL%ROW_DELIM:;%COL_DELIM:,%HAS_DEFAULTS%START_NUM_ROWS:3%\"Field Name\"%\"STRING_OR_CHOICE_ENCODED ATTRIBUTES %\"%%\"Filter\"%\"STRING_ENCODED _FILTER_REGEX \"%%\"Invert Filter\"%\"CHECKBOX _FILTER_UNMATCHED yes%no\"%no"
    CSV__GROUP_BY_DATASET = no
    CSV__IN_FIELD_NAMES = YES
    CSV__IN_SEPARATOR = ,
    CSV__SKIP_FOOTER = 0
    CSV__SKIP_LINES = 1
    CSV__SORT_TABLE_CONFIG = "NOT_OK_IF_INVALID%NO_LABEL%ROW_DELIM:;%COL_DELIM:,%HAS_DEFAULTS%START_NUM_ROWS:3%\"Attribute\"%\"STRING_OR_CHOICE_ENCODED ATTRIBUTES %\"%%\"Alpha/Num\"%\"LOOKUP_CHOICE SORT_CHOICE Alphabetic,alphabetic%Numeric,numeric\"%alphabetic%\"Order\"%\"LOOKUP_CHOICE SORT_ORDER Ascending,ascending%Descending,descending\"%ascending"
    CSV__STRIP_QUOTES = yes
    DATASET = @Value(fme_feature_type)
    FORMAT = CSV
    OUTPUT_FEATURES_DISPLAY = Schema Features
    <SCHEMA> -> AttributeRemover
AttributeRemover
    REMOVE_ATTRS = _scanZipInZip,FMEJobIdValidator,fme_format_short_name,path_windows,_inputZipFile,SourceFile_extension,fileCounter,fme_format_long_name,fileExtension,fme_feature_type_name,sourceZipFile,zipFileName,SourceFile
    -> ListSearcher
ListSearcher
    ATTR_VALUE = GridNum
    INDEX_ATTR = _list_index
    LIST_ATTR = attribute{}.name
    SEARCH_TYPE = First exact match
    FOUND -> ListExploder
    NOT_FOUND -> AttributeCreator_5
ListExploder
    ATTR_ACCUM_MODE = Merge Incoming List
    ATTR_CONFLICT_RES = Use Incoming List
    INDEX_ATTR = _element_index
    LIST_ATTR = attribute{}
    ELEMENTS -> Attr_Fields
Attr_Fields: AttributeCreator
    ATTR_TABLE:
      SET_TO FileId = @Value(FileId)
      SET_TO FieldName = @Value(name)
      SET_TO FieldType = @Value(fme_data_type)
      SET_TO Alias = FME_CONDITIONAL:DEFAULT_VALUE'@Value(name)'BOOL_OP;OR;COMPOSITE_TEST;<Unused>;TEST @LowerCase(@Value(name)) = gridnum'name_1'FME_NUM_CONDITIONS2___
      SET_TO Title
      SET_TO Description
    -> Fields (output)
Fields (output)
AttributeCreator_5
    ATTR_TABLE = SET_TO ErrorMessage = This CSV bust contain an attribute called GridNum and needs to follow the methodology described in the documentation.
    -> StringReplacer

FME custom transformer FileSystemDeleteMoveCopyExist_4
This transformer can "move","copy","delete" files. Can as well check if a file "exist" and create or delete folders.
action:The action you like to perform. 
    fileInput: provide the input file path.
    fileOutput: provide the output file path. (Is not used when you delete or test the existance of a file)

Parameters:
- Action = EXIST
- FILEINPUT = @Value(fileInput)   # Fileinput
- FILEOUTPUT =   # Fileoutput

FileName (input)
    -> ParameterFetcher
ParameterFetcher
    ATTR_LIST = action {$(Action)} fileInput {$(FILEINPUT)} fileOutput {$(FILEOUTPUT)}
    -> PythonCaller
PythonCaller
    NEW_ATTRIBUTES = "_status "
    PYTHONSOURCE:
      import fmeobjects
      # Template Function interface:
      def processFeature(feature):
          pass

      # Template Class Interface:
      class FeatureProcessor(object):
          def __init__(self):
              pass
          def input(self,feature):
              import os,shutil

              # define and get parameters
              self._status=''
              self._fileInput = feature.getAttribute('fileInput')
              self._fileOutput = feature.getAttribute('fileOutput')
              self._action = feature.getAttribute('action')

              # When action is "delete"
              if (self._action.upper() == "DELETE"):
                  if os.path.exists(self._fileInput):
                      os.remove(self._fileInput)
                      self._status='deleted'
                  else:
                      self._status='notexist:' + self._fileInput

              # When action is "delete folder"
              if (self._action.upper() == "RMDIR"):
                  if os.path.exists(self._fileInput):
                      shutil.rmtree(self._fileInput)
                      self._status='deleted'
                  else:
                      self._status='notexist:' + self._fileInput

              # When action is "copy"
              if (self._action.upper() == "COPY"):
                  if os.path.exists(self._fileInput):
                      shutil.copy(self._fileInput,self._fileOutput)
                      self._status='copied'
                  else:
                      self._status='notexist:' + self._fileInput

              # When action is "move"
              if (self._action.upper() == "MOVE"):
                  if os.path.exists(self._fileInput):
                      shutil.move(self._fileInput,self._fileOutput)
                      self._status='moved'
                  else:
                      self._status='notexist:' + self._fileInput

              # When action is " mkdir"
              if (self._action.upper() == "MKDIR"):
                  if os.path.exists(self._fileInput):
                      self._status='created'
                  else:
                      os.makedirs(self._fileInput)
                      self._status='created'

              # When action is "exist"
              if (self._action.upper() == "EXIST"):
                  if os.path.exists(self._fileInput):
                      self._status='exist'
                  else:
                      self._status='notexist:' + self._fileInput

              feature.setAttribute('_status',self._status)
              self.pyoutput(feature)
          def close(self):
              pass
    PYTHONSYMBOL = FeatureProcessor
    -> TestFilter
TestFilter
    DEFAULT_VALUE = Failed
    TEST_LIST:
      BOOL_OP,OR,COMPOSITE_TEST,<Unused>,TEST_CLAUSE,"TEST @Value(_status) = deleted
      TEST @Value(_status) = copied
      TEST @Value(_status) = moved
      TEST @Value(_status) = exist
      TEST @Value(_status) = created",Success,BOOL_OP,OR,COMPOSITE_TEST,<Unused>,TEST_CLAUSE,"TEST @Value(_status) BEGINS_WITH notexist:",DoesNotExist
    Success -> Success (output)
    DoesNotExist -> NotFound (output)
    Failed -> Failed (output)
Success (output)
NotFound (output)
Failed (output)

FME custom transformer ExtractFileFromZip
Extracts one file form a zip into a local disk. Use this together with the "getMetaDataFromZip" Transformer who tells you whats inside the zip file.
Zipsourcefile: The location towards the zip-file
    sourceFile: The sourcefile inside the zip to be extracted.
    destinationFolder: The destination folder this file should be extracted to.

Parameters:
- ZIPSOURCEFILE = @Value(zipSourceFile)   # Zipsourcefile
- SOURCEFILE = @Value(sourceFile)   # Sourcefile
- DESTINATIONFOLDER = @Value(destinationFolder)   # Destinationfolder

INPUT (input)
    -> CreateOutputFolder [FileName]
CreateOutputFolder: FileSystemDeleteMoveCopyExist
    Action = EXIST
    FILEINPUT = @Value(destinationFolder)
    Success -> unZipPython
unZipPython: PythonCaller
    NEW_ATTRIBUTES = _status
    PYTHONSOURCE:
      import fmeobjects
      import zipfile,os.path
      # Template Function interface:
      def processFeature(feature):
          pass

      # Template Class Interface:
      class FeatureProcessor(object):
          #
          # Extracts one file
          #
          def unzipOneFile(self,source_filename,filename,dest_dir):
              zfile = zipfile.ZipFile(source_filename)
              zfile.extract(filename,dest_dir)

          def __init__(self):
              pass
          def input(self,feature):
              source_filename = feature.getAttribute("zipSourceFile")
              filename = feature.getAttribute("sourceFile")
              dest_dir = feature.getAttribute("destinationFolder")
              #
              status = "success"
              # execute unzip
              #self.unzipOneFile(source_filename,filename,dest_dir)
              try:
                  self.unzipOneFile(source_filename,filename,dest_dir)
              except Exception:
                  status="failed"
                  pass
              # set if successfull
              feature.setAttribute("_status",status)
              self.pyoutput(feature)
          def close(self):
              pass
    PYTHONSYMBOL = FeatureProcessor
    -> TestFilter
TestFilter
    DEFAULT_VALUE = FAILED
    TEST_LIST = BOOL_OP,OR,COMPOSITE_TEST,<Unused>,TEST_CLAUSE,"TEST @Value(_status) = success",SUCCESS
    SUCCESS -> SUCCESS (output)
    FAILED -> RemoveFolder [FileName]
    FAILED -> Failed
SUCCESS (output)
RemoveFolder: FileSystemDeleteMoveCopyExist
    Action = EXIST
    FILEINPUT = @Value(destinationFolder)
    Success -> FAILED (output)
    Failed -> FAILED (output)
FAILED (output)
Failed: Inspector [off]

FME custom transformer FileSystemDeleteMoveCopyExist_2
This transformer can "move","copy","delete" files. Can as well check if a file "exist" and create or delete folders.
action:The action you like to perform. 
    fileInput: provide the input file path.
    fileOutput: provide the output file path. (Is not used when you delete or test the existance of a file)

Parameters:
- Action = EXIST
- FILEINPUT = @Value(fileInput)   # Fileinput
- FILEOUTPUT =   # Fileoutput

FileName (input)
    -> ParameterFetcher
ParameterFetcher
    ATTR_LIST = action {$(Action)} fileInput {$(FILEINPUT)} fileOutput {$(FILEOUTPUT)}
    -> PythonCaller
PythonCaller
    NEW_ATTRIBUTES = "_status "
    PYTHONSOURCE:
      import fmeobjects
      # Template Function interface:
      def processFeature(feature):
          pass

      # Template Class Interface:
      class FeatureProcessor(object):
          def __init__(self):
              pass
          def input(self,feature):
              import os,shutil

              # define and get parameters
              self._status=''
              self._fileInput = feature.getAttribute('fileInput')
              self._fileOutput = feature.getAttribute('fileOutput')
              self._action = feature.getAttribute('action')

              # When action is "delete"
              if (self._action.upper() == "DELETE"):
                  if os.path.exists(self._fileInput):
                      os.remove(self._fileInput)
                      self._status='deleted'
                  else:
                      self._status='notexist:' + self._fileInput

              # When action is "delete folder"
              if (self._action.upper() == "RMDIR"):
                  if os.path.exists(self._fileInput):
                      shutil.rmtree(self._fileInput)
                      self._status='deleted'
                  else:
                      self._status='notexist:' + self._fileInput

              # When action is "copy"
              if (self._action.upper() == "COPY"):
                  if os.path.exists(self._fileInput):
                      shutil.copy(self._fileInput,self._fileOutput)
                      self._status='copied'
                  else:
                      self._status='notexist:' + self._fileInput

              # When action is "move"
              if (self._action.upper() == "MOVE"):
                  if os.path.exists(self._fileInput):
                      shutil.move(self._fileInput,self._fileOutput)
                      self._status='moved'
                  else:
                      self._status='notexist:' + self._fileInput

              # When action is " mkdir"
              if (self._action.upper() == "MKDIR"):
                  if os.path.exists(self._fileInput):
                      self._status='created'
                  else:
                      os.makedirs(self._fileInput)
                      self._status='created'

              # When action is "exist"
              if (self._action.upper() == "EXIST"):
                  if os.path.exists(self._fileInput):
                      self._status='exist'
                  else:
                      self._status='notexist:' + self._fileInput

              feature.setAttribute('_status',self._status)
              self.pyoutput(feature)
          def close(self):
              pass
    PYTHONSYMBOL = FeatureProcessor
    -> TestFilter
TestFilter
    DEFAULT_VALUE = Failed
    TEST_LIST:
      BOOL_OP,OR,COMPOSITE_TEST,<Unused>,TEST_CLAUSE,"TEST @Value(_status) = deleted
      TEST @Value(_status) = copied
      TEST @Value(_status) = moved
      TEST @Value(_status) = exist
      TEST @Value(_status) = created",Success,BOOL_OP,OR,COMPOSITE_TEST,<Unused>,TEST_CLAUSE,"TEST @Value(_status) BEGINS_WITH notexist:",DoesNotExist
    Success -> Success (output)
    DoesNotExist -> NotFound (output)
    Failed -> Failed (output)
Success (output)
NotFound (output)
Failed (output)

FME custom transformer getMetaDataFromZip
Extracts the meta information from a zip including the nested zip files one level deep.
Zip file to read: The zipfile you wish to read.
Zip files inside this zip file will be extracted using zipfile1_zipfile2.zip as file name. Be aware that zips using folders who have zip files with the same name might overwrite each other in this version.

Parameters:
- inputZipFile =   # Zip file to read
- scanZipInZip = no   # Scan zip inside zip-file

InputZip (input)
    -> ParameterFetcher
Note: All none zipped files.
Counter
    CNT_ATTR = fileCounter
    DOMAIN = counter
    SCOPE = Global
    START = 0
    -> Output (output)
Output (output)

Bookmark: Retrieve parameters
ParameterFetcher
    ATTR_LIST = _inputZipFile {$(inputZipFile)} _scanZipInZip {$(scanZipInZip)}
    -> getFilesNamesInZip [zipFile]

Bookmark: First level zip file
getFilesNamesInZip
    sourceZipFile = @Value(_inputZipFile)
    Files -> TestFilter
    Files -> Counter

Bookmark: Test if content is another zip file
TestFilter
    DEFAULT_VALUE = otherFiles
    TEST_LIST:
      BOOL_OP,AND,COMPOSITE_TEST,<Unused>,TEST_CLAUSE,"TEST @Value(fileExtension) = zip
      TEST @Value(_scanZipInZip) = yes",zip in a zip
    zip in a zip -> rootFolder

Bookmark: Compile a targetFolder for the zip file
Note: We need to extract the zip file, we produce a unique name using the basename of the first zip-file and the filename of the internal zip file.
rootFolder: FilenamePartExtractor
    DIRPATH_ATTR = _dirpath
    ROOTNAME_ATTR = _zipBaseName
    SRC_ATTR = @Value(_inputZipFile)
    -> getRootRame
getRootRame: FilenamePartExtractor
    ROOTNAME_ATTR = _rootname
    SRC_ATTR = @Value(zipFileName)
    -> _newZipFolder
_newZipFolder: AttributeCreator
    ATTR_LIST = _newZipFolder,@Value(_dirpath)@Value(_zipBaseName)_@Value(_rootname)
    -> Rem_TempParams
Rem_TempParams: AttributeRemover
    REMOVE_ATTRS = _dirpath,_zipBaseName,_rootname
    -> ExtractFileFromZip

Bookmark: Unzip zip file
ExtractFileFromZip
    DESTINATIONFOLDER = @Value(_newZipFolder)
    SOURCEFILE = @Value(zipFileName)
    ZIPSOURCEFILE = @Value(_inputZipFile)
    SUCCESS -> AttributeCreator
AttributeCreator
    ATTR_LIST = path_windows,@Value(_newZipFolder)\@Value(zipFileName)
    -> AttributeRemover
AttributeRemover
    REMOVE_ATTRS = sourceZipFile,zipFileName,fileCounter,fileExtension,_newZipFolder,zipSourceFile,sourceFile,destinationFolder,action,fileInput,fileOutput,_status
    -> getFilesNames_Zip2 [zipFile]

Bookmark: Get filenames for seccond level zip
getFilesNames_Zip2: getFilesNamesInZip
    sourceZipFile = @Value(path_windows)
    Files -> Counter

FME custom transformer ExtractFileFromZip_2

Parameters:
- ZIPSOURCEFILE = @Value(zipSourceFile)   # Zipsourcefile
- SOURCEFILE = @Value(sourceFile)   # Sourcefile
- DESTINATIONFOLDER = @Value(destinationFolder)   # Destinationfolder

INPUT (input)
    -> CreateOutputFolder [FileName]
CreateOutputFolder: FileSystemDeleteMoveCopyExist
    Action = EXIST
    FILEINPUT = @Value(destinationFolder)
    Success -> unZipPython
unZipPython: PythonCaller
    NEW_ATTRIBUTES = _status
    PYTHONSOURCE:
      import fmeobjects
      import zipfile,os.path
      # Template Function interface:
      def processFeature(feature):
          pass

      # Template Class Interface:
      class FeatureProcessor(object):
          #
          # Extracts one file
          #
          def unzipOneFile(self,source_filename,filename,dest_dir):
              zfile = zipfile.ZipFile(source_filename)
              zfile.extract(filename,dest_dir)

          def __init__(self):
              pass
          def input(self,feature):
              source_filename = feature.getAttribute("zipSourceFile")
              filename = feature.getAttribute("sourceFile")
              dest_dir = feature.getAttribute("destinationFolder")
              #
              status = "success"
              # execute unzip
              #self.unzipOneFile(source_filename,filename,dest_dir)
              try:
                  self.unzipOneFile(source_filename,filename,dest_dir)
              except Exception:
                  status="failed"
                  pass
              # set if successfull
              feature.setAttribute("_status",status)
              self.pyoutput(feature)
          def close(self):
              pass
    PYTHONSYMBOL = FeatureProcessor
    -> TestFilter
TestFilter
    DEFAULT_VALUE = FAILED
    TEST_LIST = BOOL_OP,OR,COMPOSITE_TEST,<Unused>,TEST_CLAUSE,"TEST @Value(_status) = success",SUCCESS
    SUCCESS -> SUCCESS (output)
    FAILED -> RemoveFolder [FileName]
    FAILED -> Failed
SUCCESS (output)
RemoveFolder: FileSystemDeleteMoveCopyExist
    Action = EXIST
    FILEINPUT = @Value(destinationFolder)
    Success -> FAILED (output)
    Failed -> FAILED (output)
FAILED (output)
Failed: Inspector [off]

FME custom transformer FileSystemDeleteMoveCopyExist_5
This is python a based Transformer that can "move","copy","delete" and can check if a file "exist". The script is fairly simple. You have three fields.
action:"move","copy","delete","exist" 
fileInput: provide the input file path.
fileOutput: provide the output file path. (Is not used when you delete or test the existance of a file)

Parameters:
- ACTION =   # Action
- FILEINPUT = @Value(fileInput)   # Fileinput
- FILEOUTPUT =   # Fileoutput

FileName (input)
    -> PythonCaller
PythonCaller
    NEW_ATTRIBUTES = "_status "
    PYTHONSOURCE:
      import fmeobjects
      # Template Function interface:
      def processFeature(feature):
          pass

      # Template Class Interface:
      class FeatureProcessor(object):
          def __init__(self):
              pass
          def input(self,feature):
              import os,shutil

              # define and get parameters
              self._status=''
              self._fileInput = feature.getAttribute('fileInput')
              self._fileOutput = feature.getAttribute('fileOutput')
              self._action = feature.getAttribute('action')

              # When action is "delete"
              if (self._action.upper() == "DELETE"):
                  if os.path.exists(self._fileInput):
                      os.remove(self._fileInput)
                      self._status='deleted'
                  else:
                      self._status='notexist:' + self._fileInput

              # When action is "copy"
              if (self._action.upper() == "COPY"):
                  if os.path.exists(self._fileInput):
                      shutil.copy(self._fileInput,self._fileOutput)
                      self._status='copied'
                  else:
                      self._status='notexist:' + self._fileInput

              # When action is "move"
              if (self._action.upper() == "MOVE"):
                  if os.path.exists(self._fileInput):
                      shutil.move(self._fileInput,self._fileOutput)
                      self._status='moved'
                  else:
                      self._status='notexist:' + self._fileInput

              # When action is " mkdir"
              if (self._action.upper() == "MKDIR"):
                  if os.path.exists(self._fileInput):
                      self._status='created'
                  else:
                      os.mkdir(self._fileInput)
                      self._status='created'

              # When action is " rmdir"
              if (self._action.upper() == "RMDIR"):
                  if os.path.exists(self._fileInput):
                      self._status='created'
                  else:
                      os.rmdir(self._fileInput)
                      self._status='created'

              # When action is "exist"
              if (self._action.upper() == "EXIST"):
                  if os.path.exists(self._fileInput):
                      self._status='exist'
                  else:
                      self._status='notexist:' + self._fileInput

              feature.setAttribute('_status',self._status)
              self.pyoutput(feature)
          def close(self):
              pass
    PYTHONSYMBOL = FeatureProcessor
    -> TestFilter
TestFilter
    DEFAULT_VALUE = Failed
    TEST_LIST:
      BOOL_OP,OR,COMPOSITE_TEST,<Unused>,TEST_CLAUSE,"TEST @Value(_status) = deleted
      TEST @Value(_status) = copied
      TEST @Value(_status) = moved
      TEST @Value(_status) = exist
      TEST @Value(_status) = created",Success
    Success -> Success (output)
    Failed -> Failed (output)
Success (output)
Failed (output)

FME custom transformer getFilesNamesInZip_2
Retrieve the file and folder names from a zip file. The transformer is not reading the files itself. It just extracts the stored files.

Parameters:
- sourceZipFile = E:\Water\DataFlows\UWWTD_Art15_613\ReportNetData\zips\envt2nsew.zip   # Zip file to read

zipFile (input)
    -> ParameterFetcher
Note: Retrieves the files from a .zip file and expose those as features.
ParameterFetcher
    ATTR_LIST = sourceZipFile {$(sourceZipFile)}
    -> readZipContentPy
readZipContentPy: PythonCaller
    NEW_ATTRIBUTES = _zipFileContent{}
    PYTHONSOURCE:
      import fmeobjects
      # Template Function interface:
      def processFeature(feature):
          pass

      # Template Class Interface:
      class FeatureProcessor(object):
          def __init__(self):
              pass
          def input(self,feature):
              import zipfile
              # get file name form FME
              myzipfile = feature.getAttribute("sourceZipFile")
              # zipfileContent list that we will send back to FME
              _zipFileContent=[]
              # Open zip file.
              try:
                  zz = zipfile.ZipFile(myzipfile)

                  #zz.printdir()
                  for name in zz.infolist():
                      _zipFileContent.append(name.filename)
                  zz.close()
              except:
                  pass
              # send content back to FME as a list
              feature.setAttribute("_zipFileContent{}",_zipFileContent)
              self.pyoutput(feature)
          def close(self):
              pass
    PYTHONSYMBOL = FeatureProcessor
    -> ListExploder
ListExploder
    INDEX_ATTR = fileCounter
    LIST_ATTR = _zipFileContent{}
    MODE = List Elements and Original Attributes
    LIST_FOUND -> AttributeRenamer
AttributeRenamer
    ATTR_LIST = _zipFileContent,zipFileName,""
    -> FilenamePartExtractor
FilenamePartExtractor
    EXTENSION_ATTR = fileExtension
    SRC_ATTR = @Value(zipFileName)
    -> Files (output)
Files (output)

FME custom transformer FileSystemDeleteMoveCopyExist_3
This is python a based Transformer that can "move","copy","delete" and can check if a file "exist". The script is fairly simple. You have three fields.
action:"move","copy","delete","exist" 
fileInput: provide the input file path.
fileOutput: provide the output file path. (Is not used when you delete or test the existance of a file)

Parameters:
- ACTION =   # Action
- FILEINPUT = @Value(fileInput)   # Fileinput
- FILEOUTPUT =   # Fileoutput

FileName (input)
    -> PythonCaller
PythonCaller
    NEW_ATTRIBUTES = "_status "
    PYTHONSOURCE:
      import fmeobjects
      # Template Function interface:
      def processFeature(feature):
          pass

      # Template Class Interface:
      class FeatureProcessor(object):
          def __init__(self):
              pass
          def input(self,feature):
              import os,shutil

              # define and get parameters
              self._status=''
              self._fileInput = feature.getAttribute('fileInput')
              self._fileOutput = feature.getAttribute('fileOutput')
              self._action = feature.getAttribute('action')

              # When action is "delete"
              if (self._action.upper() == "DELETE"):
                  if os.path.exists(self._fileInput):
                      os.remove(self._fileInput)
                      self._status='deleted'
                  else:
                      self._status='notexist:' + self._fileInput

              # When action is "copy"
              if (self._action.upper() == "COPY"):
                  if os.path.exists(self._fileInput):
                      shutil.copy(self._fileInput,self._fileOutput)
                      self._status='copied'
                  else:
                      self._status='notexist:' + self._fileInput

              # When action is "move"
              if (self._action.upper() == "MOVE"):
                  if os.path.exists(self._fileInput):
                      shutil.move(self._fileInput,self._fileOutput)
                      self._status='moved'
                  else:
                      self._status='notexist:' + self._fileInput

              # When action is " mkdir"
              if (self._action.upper() == "MKDIR"):
                  if os.path.exists(self._fileInput):
                      self._status='created'
                  else:
                      os.mkdir(self._fileInput)
                      self._status='created'

              # When action is " rmdir"
              if (self._action.upper() == "RMDIR"):
                  if os.path.exists(self._fileInput):
                      self._status='created'
                  else:
                      os.rmdir(self._fileInput)
                      self._status='created'

              # When action is "exist"
              if (self._action.upper() == "EXIST"):
                  if os.path.exists(self._fileInput):
                      self._status='exist'
                  else:
                      self._status='notexist:' + self._fileInput

              feature.setAttribute('_status',self._status)
              self.pyoutput(feature)
          def close(self):
              pass
    PYTHONSYMBOL = FeatureProcessor
    -> TestFilter
TestFilter
    DEFAULT_VALUE = Failed
    TEST_LIST:
      BOOL_OP,OR,COMPOSITE_TEST,<Unused>,TEST_CLAUSE,"TEST @Value(_status) = deleted
      TEST @Value(_status) = copied
      TEST @Value(_status) = moved
      TEST @Value(_status) = exist
      TEST @Value(_status) = created",Success
    Success -> Success (output)
    Failed -> Failed (output)
Success (output)
Failed (output)

FME custom transformer getFilesNamesInZip
Retrieve the file and folder names from a zip file. The transformer is not reading the files itself. It just extracts the stored files.

Parameters:
- sourceZipFile = E:\Water\DataFlows\UWWTD_Art15_613\ReportNetData\zips\envt2nsew.zip   # Zip file to read

zipFile (input)
    -> ParameterFetcher
Note: Retrieves the files from a .zip file and expose those as features.
ParameterFetcher
    ATTR_LIST = sourceZipFile {$(sourceZipFile)}
    -> readZipContentPy
readZipContentPy: PythonCaller
    NEW_ATTRIBUTES = _zipFileContent{}
    PYTHONSOURCE:
      import fmeobjects
      # Template Function interface:
      def processFeature(feature):
          pass

      # Template Class Interface:
      class FeatureProcessor(object):
          def __init__(self):
              pass
          def input(self,feature):
              import zipfile
              # get file name form FME
              myzipfile = feature.getAttribute("sourceZipFile")
              # zipfileContent list that we will send back to FME
              _zipFileContent=[]
              # Open zip file.
              try:
                  zz = zipfile.ZipFile(myzipfile)

                  #zz.printdir()
                  for name in zz.infolist():
                      _zipFileContent.append(name.filename)
                  zz.close()
              except:
                  pass
              # send content back to FME as a list
              feature.setAttribute("_zipFileContent{}",_zipFileContent)
              self.pyoutput(feature)
          def close(self):
              pass
    PYTHONSYMBOL = FeatureProcessor
    -> ListExploder
ListExploder
    INDEX_ATTR = fileCounter
    LIST_ATTR = _zipFileContent{}
    MODE = List Elements and Original Attributes
    LIST_FOUND -> AttributeRenamer
AttributeRenamer
    ATTR_LIST = _zipFileContent,zipFileName,""
    -> FilenamePartExtractor
FilenamePartExtractor
    EXTENSION_ATTR = fileExtension
    SRC_ATTR = @Value(zipFileName)
    -> Files (output)
Files (output)
