FME workspace OptimiseAndUploadDimensionFieldParts.fmw
Title: OptimiseAndUploadDimensionFile

Parameters:
- FileId =

Writers:
- MSSQL_JDBC_NONSPATIAL_1: MSSQL_JDBC_NONSPATIAL to CubeManager

Note: Get meta data on file / to be processed...
SQLCreator
    DATASET = CubeManager
    EXPOSED_ATTRIBUTE_LIST = CubeDimensionId FileId SourceFile GridCellSpacing Name
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = CubeManager
    MSSQL_ADO_QUERY_FEATURE_TYPES_FOR_MERGE_FILTERS = Yes
    SQL_STATEMENT:
      select  CubeDimensions.CubeDimensionId,
              CubeDimensions.Name,
              GridTypes.name as GridTypesShortName,
              GridTypes.XCellSpacing as GridCellSpacing,
              Files.FileId,
              SourceFile
      from CubeDimensions
      inner join Files on CubeDimensions.CubeDimensionId = Files.CubeDimensionId
      inner join GridTypes on GridTypes.GridTypeId = Cubedimensions.GridTypeId
      where FileId = $(FileId)

      /*
      select  CubeDimensions.CubeDimensionId,
              CubeDimensions.Name,
              GridTypes.name as GridTypesShortName,
              GridTypes.XCellSpacing as GridCellSpacing,
              Files.FileId,
              Files.SourceFile
      from CubeDimensions
      inner join Files on CubeDimensions.CubeDimensionId = Files.CubeDimensionId
      inner join GridTypes on GridTypes.GridTypeId = Cubedimensions.GridTypeId
      where FileId = $(FileId)
      */
    RESULT -> SetJobId
    <REJECTED> -> Initial_SQL_Failed
JediLogWritter_startjob_5
    FILEID = $(FileId)
    MESSAGESTRING = Start validation process
    MESSAGETYPE = INFO
    OBJECTPROCESSED = Dimension
    SQLServerConn = CubeManager
    TRANSFORMERPATH = $(WORKSPACE_NAME)\OptimiseAndUploadDimensionFile
    -> ExtractAndOptimiseRasters [Raster]
Note: Write Error back to database
SQLExecutor_Error_2
    COMBINE_ATTRS = Result Attributes Only
    COMBINE_GEOM = Initiator Geometry Only
    DATASET = CubeManager
    FORMAT = MSSQL_ADO
    MSSQL_ADO_COMMAND_TIMEOUT = 30
    MSSQL_ADO_CREATE_FEATURE_TABLES_FROM_DATA = Yes
    MSSQL_ADO_NAMED_CONNECTION = CubeManager
    MSSQL_ADO_QUERY_FEATURE_TYPES_FOR_MERGE_FILTERS = Yes
    SQL_STATEMENT:
      Update dbo.Files
          set ErrorMessages = 'Raster2GridV2.fmw: Process aborted! Path "@Value(__TempDimensionLocationPath)" was not found!',
      where FileId = @Value(FileId)
    INITIATOR -> Error
    <REJECTED> -> Error
Initial_SQL_Failed: Terminator
    MESSAGE = Translation Terminated

Bookmark: Tell DB we are executing the job
Note: Reset the database and provide the job_id so log information can be found easily.
SetJobId: AttributeCreator
    ATTR_TABLE = SET_TO _FME_JOB_ID = FME_CONDITIONAL:DEFAULT_VALUE'$(FME_JOB_ID)'BOOL_OP;AND;COMPOSITE_TEST;<Unused>;TEST $(FME_JOB_ID) ATTRIBUTE_IS_MISSING _FME_BLANK_STRING_;TEST $(FME_JOB_ID) NOT_ATTRIBUTE_HAS_VALUE _FME_BLANK_STRING_'-1'FME_NUM_CONDITIONS2___
    -> Store_File_Info_2 [INITIATOR]
Store_File_Info_2: SQLExecutor
    COMBINE_ATTRS = Result Attributes Only
    COMBINE_GEOM = Initiator Geometry Only
    DATASET = CubeManager
    FORMAT = MSSQL_ADO
    MSSQL_ADO_COMMAND_TIMEOUT = 30
    MSSQL_ADO_CREATE_FEATURE_TABLES_FROM_DATA = Yes
    MSSQL_ADO_NAMED_CONNECTION = CubeManager
    MSSQL_ADO_QUERY_FEATURE_TYPES_FOR_MERGE_FILTERS = Yes
    SQL_STATEMENT:
      Update dbo.Files
          set [FMEJobIdSourceUploaded]=@Value(_FME_JOB_ID),
              FMEJobIdValidator = @Value(_FME_JOB_ID),
              [AzureSourceUploaded]=NULL,
              [FMEJobIdSourceUploadStatus]=0
      where FileId = @Value(FileId)
    INITIATOR -> JediLogWritter_startjob
    <REJECTED> -> Initial_SQL_Failed
JediLogWritter_startjob
    FILEID = $(FileId)
    MESSAGESTRING = Conversion started
    MESSAGETYPE = INFO
    OBJECTPROCESSED = Dimension
    SQLServerConn = CubeManager
    TRANSFORMERPATH = $(WORKSPACE_NAME)\OptimiseAndUploadDimensionFile
    -> SQLExecutor [INITIATOR]

Bookmark: Get Temp Folder path for uncompressing zip file
Note: Find Dimension temp path
SQLExecutor
    COMBINE_ATTRS = Keep Initiator Attributes if Conflict
    COMBINE_GEOM = Initiator Geometry Only
    DATASET = CubeManager
    EXPOSED_ATTRIBUTE_LIST = __TempDimensionLocationPath
    FORMAT = MSSQL_ADO
    MSSQL_ADO_COMMAND_TIMEOUT = 30
    MSSQL_ADO_CREATE_FEATURE_TABLES_FROM_DATA = Yes
    MSSQL_ADO_NAMED_CONNECTION = CubeManager
    MSSQL_ADO_QUERY_FEATURE_TYPES_FOR_MERGE_FILTERS = Yes
    SQL_STATEMENT:
      select AttributeValue + '\@Value(Name)' as __TempDimensionLocationPath
      from dbo.GeneralInfo
      where AttributeName = 'DimensionTempLocation'
    RESULT -> Logger
    <REJECTED> -> Initial_SQL_Failed
Logger
    MAXCOORDS = 1
    MAXFEATS = 1
    MESSAGE = Attribute information
    LOGGED -> IsProduction_
IsProduction_: Tester
    BOOL_OP = OR
    COMPOSITE_TEST = 1
    TEST_CLAUSE = TEST @Value(_FME_JOB_ID) != -1
    TEST_MODE = TEST
    PASSED -> FileSystemDeleteMoveCopyExist_2 [FileName]
    FAILED -> CreateLocalTempPath
Note: For testing in desktop
CreateLocalTempPath: AttributeCreator
    ATTR_TABLE:
      SET_TO SourceFile = S:\Common workspace\CrossProjects\Jedi\Bilbomatica\Oskar\Temp\N2k2021_10m_C.zip
      SET_TO __TempDimensionLocationPath = S:\Common workspace\CrossProjects\Jedi\Bilbomatica\Testing\
    -> FileSystemDeleteMoveCopyExist_2 [FileName]

Bookmark: Create Folder for Uncompressing Zipped Files
Note: Remove Temp (__TempDimensionLocationPath)
FileSystemDeleteMoveCopyExist_2
    Action = RMDIR
    FILEINPUT = @Value(__TempDimensionLocationPath)
    Success -> FileSystemDeleteMoveCopyExist [FileName]
    NotFound -> FileSystemDeleteMoveCopyExist [FileName]
    Failed -> FileSystemDeleteMoveCopyExist [FileName]
Note: Create TEMP (__TempDimensionLocationPath)
FileSystemDeleteMoveCopyExist: FileSystemDeleteMoveCopyExist_2
    Action = MKDIR
    FILEINPUT = @Value(__TempDimensionLocationPath)
    Success -> ValidateZipContent
    NotFound -> SQLExecutor_Error_2 [INITIATOR]

Bookmark: Find out if the content is correct.
ValidateZipContent
    SOURCEFILE = @Value(SourceFile)
    TifFile -> Sampler
    Error -> JediLogWritter_startjob_8
Sampler
    RATE = 1
    SAMPLE_MODE = No
    SAMPLE_TYPE_LONG = First N Features
    SAMPLED -> JediLogWritter_startjob_7
JediLogWritter_startjob_7
    FILEID = $(FileId)
    MESSAGESTRING = ZipFIle validated
    MESSAGETYPE = INFO
    OBJECTPROCESSED = Dimension
    SQLServerConn = CubeManager
    TRANSFORMERPATH = $(WORKSPACE_NAME)\OptimiseAndUploadDimensionFile
    -> SQLExecutor_Accepted [INITIATOR]
Note: Set Validated = 1
SQLExecutor_Accepted
    COMBINE_ATTRS = Result Attributes Only
    COMBINE_GEOM = Initiator Geometry Only
    DATASET = CubeManager
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = CubeManager
    MSSQL_ADO_QUERY_FEATURE_TYPES_FOR_MERGE_FILTERS = Yes
    SQL_STATEMENT:
      Update dbo.Files
          set Validated =1
      where FileId = @Value(FileId)
    INITIATOR -> JediLogWritter_startjob_5
    <REJECTED> -> ErrorUpdatingDB
JediLogWritter_startjob_8
    FILEID = $(FileId)
    MESSAGESTRING = ZipFile NO Valid
    MESSAGETYPE = INFO
    OBJECTPROCESSED = Dimension
    SQLServerConn = CubeManager
    TRANSFORMERPATH = $(WORKSPACE_NAME)\OptimiseAndUploadDimensionFile
    -> SQLExecutor_Error [INITIATOR]
Note: Set Validated = 0
SQLExecutor_Error
    COMBINE_ATTRS = Result Attributes Only
    COMBINE_GEOM = Initiator Geometry Only
    DATASET = CubeManager
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = CubeManager
    MSSQL_ADO_QUERY_FEATURE_TYPES_FOR_MERGE_FILTERS = Yes
    SQL_STATEMENT:
      Update dbo.Files
          set Validated = 0,
              ErrorMessages = '@Value(ErrorMessage)',
              FMEJobIdValidator=@Value(_FME_JOB_ID)
      where FileId = @Value(FileId)
    <REJECTED> -> ErrorUpdatingDB_2

Bookmark: Process rasters and upload to Azure Blob Storage
Note: Extract the files from Zip file. Create one tif for each band and optimise them. Create a zipped file with all of the tif files
ExtractAndOptimiseRasters: ConvertImageToDimensionINT8
    FILEID = @Value(FileId)
    FME_JOBID = @Value(_FME_JOB_ID)
    GRIDCELLSPACING = @Value(GridCellSpacing)
    NAME = @Value(Name)
    SOURCEFILE = @Value(SourceFile)
    __TEMPDIMENSIONLOCATIONPATH = @Value(__TempDimensionLocationPath)
    OptimisedRaster -> JediLogWritter_startjob_2
    CategoryDefinition -> UpdateAttributesInCubeManager
    Failed -> ErrorHandlingRasters
JediLogWritter_startjob_2
    FILEID = $(FileId)
    MESSAGESTRING = Upload file to Azure blob
    MESSAGETYPE = INFO
    OBJECTPROCESSED = Dimension
    SQLServerConn = CubeManager
    TRANSFORMERPATH = $(WORKSPACE_NAME)\OptimiseAndUploadDimensionFile
    -> UploadFilesToAzure [UploadFilesToDBFS]
Note: Upload zipped file to Azure Blob Storage
UploadFilesToAzure: UploadFilesToHDFS
    DIMENSIONNAME = @Value(DimensionName)
    OUTPUTFILENAME = @Value(_source_filename)
    _DATASET = @Value(SourceFile)
    -> Store_File_Info [INITIATOR]
    Error -> ErrorUploadingToBlob

Bookmark: Update Results in Database
Note: Update dbo.Files / set [DimensionFile] = '@Value(__TempDimensionLocationPath)', / [DimensionFileCreated]=getdate(), / [FMEJobIdDimensionProcessStatus]=1 / ErrorMessages = Null / where FileId = @Value(FileId)
Store_File_Info: SQLExecutor
    COMBINE_ATTRS = Result Attributes Only
    COMBINE_GEOM = Initiator Geometry Only
    DATASET = CubeManager
    FORMAT = MSSQL_ADO
    MSSQL_ADO_COMMAND_TIMEOUT = 60
    MSSQL_ADO_CREATE_FEATURE_TABLES_FROM_DATA = Yes
    MSSQL_ADO_NAMED_CONNECTION = CubeManager
    MSSQL_ADO_QUERY_FEATURE_TYPES_FOR_MERGE_FILTERS = Yes
    SQL_STATEMENT:
      Update dbo.Files
          set [AzureSourceFile] = '@Value(destFile)',
              [AzureSourceUploaded]=getdate(),
              [FMEJobIdSourceUploadStatus]=1,
              ErrorMessages = Null
      where FileId = $(FileId)
    INITIATOR -> ConversionOKDetails
    <REJECTED> -> ConversionFailedDetails

Bookmark: Build Process Info details
ConversionOKDetails: AttributeCreator
    ATTR_TABLE:
      SET_TO TransformerPath = StoreFileInfo
      SET_TO MessageString = Conversion completed successfully
      SET_TO MessageType = INFO
    -> Junction_6
ConversionFailedDetails: AttributeCreator
    ATTR_TABLE:
      SET_TO TransformerPath = StoreFileInfo
      SET_TO MessageString = @Value(_reader_error)
      SET_TO MessageType = ERROR
    -> Junction_4
ErrorUploadingToBlob: AttributeCreator
    ATTR_TABLE:
      SET_TO TransformerPath = UploadFilesToAzure
      SET_TO MessageString = @Value(_azure_blob_uploader_error_message)
    -> Junction_3

Bookmark: WRITE ATTRIBUTE INFORMATION
Note: Write the attribute definitions inside the database...
UpdateAttributesInCubeManager
    ALIAS = @Value(Alias)
    DESCRIPTION = @Value(Title)
    EXCLUDEVALUES = @Value(ExcludeValues)
    FIELDNAME = @Value(FieldName)
    FIELDTYPE = @Value(FieldType)
    FILEID = @Value(FileId)
    FileId = @Value(FileId)
    PARENTZIP = @Value(ParentZip)
    TIFFILES = @Value(numTifFiles)
    TITLE = @Value(Description)
    _FILENAME = @Value(_filename)
    <Rejected> -> Junction_3

Bookmark: Build Error Info Details
ErrorHandlingRasters: AttributeCreator
    ATTR_TABLE:
      SET_TO TransformerPath = ExtractAndOPtimiseRaster
      SET_TO MessageString = @Value(_error)
      SET_TO MessageType = ERROR
    -> Junction_3
ErrorUpdatingDB: AttributeCreator
    ATTR_TABLE:
      SET_TO TransformerPath = SQLExecutor_Accepted
      SET_TO MessageString = @Value(_reader_error)
      SET_TO MessageType = ERROR
    -> Junction_3
ErrorUpdatingDB_2: AttributeCreator
    ATTR_TABLE:
      SET_TO TransformerPath = SQLExecutor_Error
      SET_TO MessageString = @Value(_reader_error)
      SET_TO MessageType = ERROR
    -> Junction_4
Error: AttributeCreator
    ATTR_TABLE:
      SET_TO TransformerPath = SQLExecutor_Error_2
      SET_TO MessageString = OptimiseAndUploadDimensionFile.fmw: Process aborted! Path @Value(__TempDimensionLocationPath), was not found!
      SET_TO MessageStringInfo = OptimiseAndUploadDimensionFile.fmw: Process aborted! Path @Value(__TempDimensionLocationPath), was not found!
      SET_TO MessageType = ERROR

Bookmark: WRITE ERROR IN DB
Junction_3
    -> SQLExecutor_WriteErrorMessage [INITIATOR]
SQLExecutor_WriteErrorMessage
    COMBINE_ATTRS = Result Attributes Only
    COMBINE_GEOM = Initiator Geometry Only
    DATASET = CubeManager
    FORMAT = MSSQL_ADO
    MSSQL_ADO_COMMAND_TIMEOUT = 30
    MSSQL_ADO_CREATE_FEATURE_TABLES_FROM_DATA = Yes
    MSSQL_ADO_NAMED_CONNECTION = CubeManager
    MSSQL_ADO_QUERY_FEATURE_TYPES_FOR_MERGE_FILTERS = Yes
    SQL_STATEMENT:
      Update dbo.Files
          set ErrorMessages = '@Value(MessageString)'
      where FileId =@Value(FileId)
    INITIATOR -> AttributeCreator_5
    <REJECTED> -> AttributeCreator_4
AttributeCreator_5
    ATTR_TABLE:
      SET_TO TransformerPath = WRITE ERROR IN DB
      SET_TO MessageString = @Value(MessageString)
    -> Junction_10
Note: INFO
Junction_10
    -> Junction_6
AttributeCreator_4
    ATTR_TABLE:
      SET_TO TransformerPath = WRITE ERROR IN DB
      SET_TO MessageString = @Value(MessageString)
        Error Running SQLExecutor_WriteErrorMessage

        WorkSpace: $(WORKSPACE_NAME)
    -> Junction_9
Note: ERROR
Junction_9
    -> Junction_4

Bookmark: WRITE LOGS
Note: INFO
Junction_6
    -> AttributeCreator_INFO
AttributeCreator_INFO
    ATTR_TABLE = SET_TO MessageType = FME_CONDITIONAL:DEFAULT_VALUE'@Value(MessageType)'BOOL_OP;OR;COMPOSITE_TEST;1;TEST MessageType ATTRIBUTE_VALUE_NULL _FME_BLANK_STRING_'INFO'FME_NUM_CONDITIONS2___
    -> AttributeKeeper_2
Note: ERROR
Junction_4
    -> AttributeCreator_ERROR
AttributeCreator_ERROR
    ATTR_TABLE = SET_TO MessageType = ERROR
    -> AttributeKeeper_2
AttributeKeeper_2
    CREATE_BULK_MODE_FEATURES = No
    KEEP_ATTRS = MessageType,TransformerPath,MessageString,FileId
    -> JediLogWritter
JediLogWritter
    FILEID = $(FileId)
    MESSAGESTRING = @Value(MessageString)
    MESSAGETYPE = @Value(MessageType)
    OBJECTPROCESSED = Dimension
    SQLServerConn = CubeManager
    TRANSFORMERPATH = $(WORKSPACE_NAME)\CreateDtabricksDimension
    -> Tester
Tester
    BOOL_OP = OR
    COMPOSITE_TEST = 1
    TEST_CLAUSE = TEST @Value(MessageType) = ERROR
    TEST_MODE = TEST
    PASSED -> Terminator_2
Terminator_2
    MESSAGE = Translation Terminated: @Value(MessageString)

FME custom transformer UpdateAttributesInCubeManager
Updates the field attributes inside CubeManager.

Parameters:
- ALIAS =
- DESCRIPTION =
- EXCLUDEVALUES =
- FIELDNAME =
- FIELDTYPE =
- FILEID =
- FileId =
- PARENTZIP =
- TIFFILES =
- TITLE =
- _FILENAME =

Input (input)
    -> IsNestedFieldPart
Output (output)
<Rejected> (output)

Bookmark: Set Exclude values of the field part
IsNestedFieldPart: TestFilter
    DEFAULT_VALUE = Nested
    TEST_LIST = "BOOL_OP,OR,COMPOSITE_TEST,""""""1"""""",TEST_CLAUSE,TEST ParentZip ATTRIBUTE_VALUE_NULL """,NotNested
    NotNested -> SetExcludeValue [INITIATOR]
    Nested -> FieldName_ParentZip
FieldName_ParentZip: AttributeCreator
    ATTR_TABLE = SET_TO FieldName = @Value(ParentZip)
    -> SetExcludeValue [INITIATOR]
SetExcludeValue: SQLExecutor
    COMBINE_ATTRS = Result Attributes Only
    COMBINE_GEOM = Initiator Geometry Only
    DATASET = CubeManager
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = CubeManager
    MSSQL_ADO_QUERY_FEATURE_TYPES_FOR_MERGE_FILTERS = Yes
    SQL_STATEMENT:
      declare @fieldId bigint

      select @fieldId =  fieldId from fields where fileid = @Value(FileId) and fieldname='@Value(FieldName)'

      if not (exists(SELECT [FilePartId]
      	FROM FieldParts
      	where
      		FieldParts.FieldId =@fieldId  and FieldParts.FileName = '@Value(_filename)'))

      	BEGIN


      		INSERT INTO FieldParts(FieldId, FileName,ExcludedValues)
      		VALUES (
      			@fieldId , '@Value(_filename)', @Value(ExcludeValues)
      		)

      	END

      else
          update [FieldParts]
          set ExcludedValues = @Value(ExcludeValues)
          where [FilePartId] =

          (
          SELECT [FilePartId]

          FROM [CubeManager].[dbo].[FieldParts]
          WHERE
              FieldParts.FieldId =@fieldId   and FieldParts.FileName ='@Value(_filename)'
          )
    INITIATOR -> Aggregator
    <REJECTED> -> <Rejected> (output)

Bookmark: Set the datatype of the field
Aggregator
    ACCUM_ATTRS_NAME = Use Attributes From One Feature
    AGGREGATE_TYPE = Homogeneous Collection (If Possible)
    CONCAT_ATTRS = FieldType
    GROUP_BY = FieldName
    MODE = Geometry - Assemble One Level
    SEP = ,
    AGGREGATE -> GetFieldDataType
GetFieldDataType: AttributeCreator
    ATTR_TABLE = SET_TO _dataType = FME_CONDITIONAL:DEFAULT_VALUE'float'BOOL_OP;OR;COMPOSITE_TEST;1;CASE_INSENSITIVE_TEST @Value(FieldType) CONTAINS float'float'BOOL_OP;OR;COMPOSITE_TEST;1;CASE_INSENSITIVE_TEST @Value(FieldType) CONTAINS bigint'bigint'BOOL_OP;OR;COMPOSITE_TEST;1;CASE_INSENSITIVE_TEST @Value(FieldType) CONTAINS smallint'smallint'BOOL_OP;OR;COMPOSITE_TEST;1;CASE_INSENSITIVE_TEST @Value(FieldType) CONTAINS tinyint'tinyint'BOOL_OP;OR;COMPOSITE_TEST;1;CASE_INSENSITIVE_TEST @Value(FieldType) CONTAINS int'int'FME_NUM_CONDITIONS6___
    -> SetFieldDataType [INITIATOR]
SetFieldDataType: SQLExecutor
    COMBINE_ATTRS = Result Attributes Only
    COMBINE_GEOM = Initiator Geometry Only
    DATASET = CubeManager
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = CubeManager
    MSSQL_ADO_QUERY_FEATURE_TYPES_FOR_MERGE_FILTERS = Yes
    SQL_STATEMENT:
      update [Fields]
      set FieldType= '@Value(_dataType)'
      where [FieldId] =

      (
      SELECT [FieldId]

      FROM [CubeManager].[dbo].[Fields]
      where
      	fields.FieldName = '@Value(FieldName)' and
      	fields.FileId = @Value(FileId)
      )
    INITIATOR -> Output (output)
    <REJECTED> -> <Rejected> (output)

FME custom transformer ExtractFileFromZip
Extracts one file form a zip into a local disk. Use this together with the "getMetaDataFromZip" Transformer who tells you whats inside the zip file.
Zipsourcefile: The location towards the zip-file
    sourceFile: The sourcefile inside the zip to be extracted.
    destinationFolder: The destination folder this file should be extracted to.

Parameters:
- DESTINATIONFOLDER =
- SOURCEFILE =
- ZIPSOURCEFILE =

INPUT (input)
    -> Tester
Note: Extract only files with zip or tif extension
Tester
    BOOL_OP = OR
    COMPOSITE_TEST = 1 OR 2
    TEST_CLAUSE:
      CASE_INSENSITIVE_TEST @LowerCase(@Value(sourceFile)) ENDS_WITH zip
      CASE_INSENSITIVE_TEST @LowerCase(@Value(sourceFile)) ENDS_WITH tif
    TEST_MODE = TEST
    PASSED -> FolderExists [FileName]
Note: Create a new folder for the target file if it doesn´t exist
FolderExists: FileSystemDeleteMoveCopyExist
    Action = EXIST
    FILEINPUT = @Value(destinationFolder)
    Success -> unZipPython
    NotFound -> CreateOutputFolder [FileName]
Note: Create a new folder for the target file if it doesn´t exist
CreateOutputFolder: FileSystemDeleteMoveCopyExist
    Action = MKDIR
    FILEINPUT = @Value(destinationFolder)
    Success -> unZipPython
    Failed -> FAILED (output)
Note: Extract file from Zip
unZipPython: PythonCaller
    NEW_ATTRIBUTES = _status
    PYTHONSOURCE:
      import fmeobjects
      import zipfile,os.path
      #import subprocess, sys

      # Template Function interface:
      def processFeature(feature):
          pass

      # Template Class Interface:
      class FeatureProcessor(object):
          #
          # Extracts one file
          #
          def unzipOneFile(self,source_filename,filename,dest_dir):
              zfile = zipfile.ZipFile(source_filename)
              zfile.extract(filename,dest_dir)

          def __init__(self):
              pass
          def input(self,feature):
              source_filename = feature.getAttribute("zipSourceFile")
              filename = feature.getAttribute("sourceFile")
              dest_dir = feature.getAttribute("destinationFolder")
              #
              status = "success"
              # execute unzip
              #self.unzipOneFile(source_filename,filename,dest_dir)
              try:
                  self.unzipOneFile(source_filename,filename,dest_dir)
                  #subprocess.Popen(["7z", "e", source_filename, "-o", dest_dir, filename,"-y"])
              except Exception as e:
                  print("******")
                  print("ERROR=" + str(e))
                  print("Filename=" + filename)
                  print("******")
                  status="failed"
                  pass
              # set if successfull
              feature.setAttribute("_status",status)
              self.pyoutput(feature)
          def close(self):
              pass
    PYTHONSYMBOL = FeatureProcessor
    -> TestFilter
Note: Chech Python caller result
TestFilter
    DEFAULT_VALUE = FAILED
    TEST_LIST = BOOL_OP,OR,COMPOSITE_TEST,<Unused>,TEST_CLAUSE,"TEST @Value(_status) = success",SUCCESS
    SUCCESS -> SUCCESS (output)
    FAILED -> RemoveFolder [FileName]
SUCCESS (output)
Note: Remove target folder if the unzip operation fails
RemoveFolder: FileSystemDeleteMoveCopyExist
    Action = EXIST
    FILEINPUT = @Value(destinationFolder)
    Success -> FAILED (output)
    Failed -> FAILED (output)
FAILED (output)

FME custom transformer ValidateZipContent

Parameters:
- SOURCEFILE =

Input (input)
    -> FilenamePartExtractor
TifFile (output)
Inspector [off]
Note: No tif file in zip
SetErrorMessage: AttributeCreator
    ATTR_TABLE = SET_TO ErrorMessage = Tif file is missing in the Zip
    -> getMetaDataFromZip_FAILED_-__Failed
Note: Zip file doesn´t exist
SetErrorMessage_4: AttributeCreator
    ATTR_TABLE = SET_TO ErrorMessage = Zip file doesn´t exist
    -> getMetaDataFromZip_FAILED_-__Failed
getMetaDataFromZip_FAILED_-__Failed: Junction
    -> Error (output)
Error (output)

Bookmark: Check Source File
Note: Check if SourceFile has .zip extension and if it exist
FilenamePartExtractor
    EXTENSION_ATTR = SourceFile_extension
    SRC_ATTR = @Value(SourceFile)
    -> TestZipFile
TestZipFile: TestFilter
    DEFAULT_VALUE = OtherFormat
    TEST_LIST = BOOL_OP,OR,COMPOSITE_TEST,<Unused>,TEST_CLAUSE,"TEST @LowerCase(@Value(SourceFile_extension)) = zip",IsAZipFile
    IsAZipFile -> ZipFileExists [FileName]
    OtherFormat -> SetErrorMessage_3
Note: Does zip file exist?
ZipFileExists: FileSystemDeleteMoveCopyExist_2
    Action = EXIST
    FILEINPUT = @Value(SourceFile)
    Success -> getMetaDataFromZip [InputZip]
    NotFound -> SetErrorMessage_4
Note: No zip file
SetErrorMessage_3: AttributeCreator
    ATTR_TABLE = SET_TO ErrorMessage = File must be a .zip that contains at least a GeoTif file.
    -> getMetaDataFromZip_FAILED_-__Failed

Bookmark: Read zip and find .tiff
getMetaDataFromZip
    inputZipFile = @Value(SourceFile)
    scanZipInZip = yes
    -> StringSearcher
    ERROR -> SetErrorMessage
StringSearcher
    CASE = no
    MATCHED_RESULT_ATTR = _zipFileBaseName
    REGEXP = ^[^.]+
    STRING_TO_SEARCH = @Value(zipFileName)
    MATCHED -> AttributeCreator_3
AttributeCreator_3
    ATTR_TABLE = SET_TO _zipFileBaseName_lowercase = @LowerCase(@Value(_zipFileBaseName))
    -> Aggregator
    -> TestFilter_2
Aggregator [off]
    ACCUM_ATTRS_NAME = Get Attributes From One Representative Feature
    AGGREGATE_TYPE = Homogeneous Collection (If Possible)
    CONCAT_ATTRS = zipFileName fileExtension
    GROUP_BY = SourceFile _zipFileBaseName_lowercase
    MODE = Geometry - Assemble One Level
    ORDERED = No
    SEP = ,
    AGGREGATE -> Inspector
    AGGREGATE -> TestFilter_2

Bookmark: FIlter tif files only
TestFilter_2
    DEFAULT_VALUE = NoTifFile
    TEST_LIST:
      "BOOL_OP,AND,COMPOSITE_TEST,""""""1 AND 2"""""",TEST_CLAUSE,CASE_INSENSITIVE_TEST @LowerCase(@Value(fileExtension)) ENDS_WITH tif
      CASE_INSENSITIVE_TEST @Value(zipFileName) NOT_BEGINS_WITH __MACOSX",Tif File
    Tif File -> TifFile (output)

FME custom transformer FileSystemDeleteMoveCopyExist
This transformer can "move","copy","delete" files. Can as well check if a file "exist" and create or delete folders.
action:The action you like to perform. 
    fileInput: provide the input file path.
    fileOutput: provide the output file path. (Is not used when you delete or test the existance of a file)

Parameters:
- Action =
- FILEINPUT =
- FILEOUTPUT =

FileName (input)
    -> ParameterFetcher
ParameterFetcher
    ATTR_LIST = action {$(Action)} fileInput {$(FILEINPUT)} fileOutput {$(FILEOUTPUT)}
    -> PythonCaller
PythonCaller
    NEW_ATTRIBUTES = "_status "
    PYTHONSOURCE:
      import fmeobjects
      # Template Function interface:
      def processFeature(feature):
          pass

      # Template Class Interface:
      class FeatureProcessor(object):
          def __init__(self):
              pass
          def input(self,feature):
              import os,shutil

              # define and get parameters
              self._status=''
              self._fileInput = feature.getAttribute('fileInput')
              self._fileOutput = feature.getAttribute('fileOutput')
              self._action = feature.getAttribute('action')

              # When action is "delete"
              if (self._action.upper() == "DELETE"):
                  if os.path.exists(self._fileInput):
                      os.remove(self._fileInput)
                      self._status='deleted'
                  else:
                      self._status='notexist:' + self._fileInput

              # When action is "delete folder"
              if (self._action.upper() == "RMDIR"):
                  if os.path.exists(self._fileInput):
                      shutil.rmtree(self._fileInput)
                      self._status='deleted'
                  else:
                      self._status='notexist:' + self._fileInput

              # When action is "copy"
              if (self._action.upper() == "COPY"):
                  if os.path.exists(self._fileInput):
                      shutil.copy(self._fileInput,self._fileOutput)
                      self._status='copied'
                  else:
                      self._status='notexist:' + self._fileInput

              # When action is "move"
              if (self._action.upper() == "MOVE"):
                  if os.path.exists(self._fileInput):
                      shutil.move(self._fileInput,self._fileOutput)
                      self._status='moved'
                  else:
                      self._status='notexist:' + self._fileInput

              # When action is " mkdir"
              if (self._action.upper() == "MKDIR"):
                  if os.path.exists(self._fileInput):
                      self._status='created'
                  else:
                      os.makedirs(self._fileInput)
                      self._status='created'

              # When action is "exist"
              if (self._action.upper() == "EXIST"):
                  if os.path.exists(self._fileInput):
                      self._status='exist'
                  else:
                      self._status='notexist:' + self._fileInput

              feature.setAttribute('_status',self._status)
              self.pyoutput(feature)
          def close(self):
              pass
    PYTHONSYMBOL = FeatureProcessor
    -> TestFilter
TestFilter
    DEFAULT_VALUE = Failed
    TEST_LIST:
      BOOL_OP,OR,COMPOSITE_TEST,<Unused>,TEST_CLAUSE,"TEST @Value(_status) = deleted
      TEST @Value(_status) = copied
      TEST @Value(_status) = moved
      TEST @Value(_status) = exist
      TEST @Value(_status) = created",Success,BOOL_OP,OR,COMPOSITE_TEST,<Unused>,TEST_CLAUSE,"TEST @Value(_status) BEGINS_WITH notexist:",DoesNotExist
    Success -> Success (output)
    DoesNotExist -> NotFound (output)
    Failed -> Failed (output)
Success (output)
NotFound (output)
Failed (output)

FME custom transformer AzureBlobUploader
Uploads a file to Azure using the Azure Blob Service REST API (https://msdn.microsoft.com/en-us/library/azure/dd135733.aspx)
A key is needed as well as the name of the storage account.
Source data can be either from an attribute or a filepath.
Maximum file size is roughly 195 GB. 
Files larger than 64 MB will be uploaded in chunks of 4 MB.
Storage account: 
Provide the storage account. Look for this under the portal.azure.com.
Access key: 
Provide the access key for the blob inside Azure. You can find this when you select the storage inside the protal.azure.com website, go to settings and then search for "Access keys".
Use access keys to authenticate your applications when making requests to this Azure storage account. Store your access keys securely - for example, using Azure Key Vault - and don't share them. We recommend regenerating your access keys regularly. You are provided two access keys so that you can maintain connections using one key while regenerating the other. 
Container name: 
The storage countainer name. These are listed directly under the storage account pannel. 
Blob name: 
The name of the blob you are about to create. The filename of the source data will be used if this was not provided. You can create folders by simply using the '/' for example "folder1/folder2/blobname". 
Upload from: 
Describes what is provided inside the "source data" attribute. When set to "AttributeValue" it means that the source data is a binary file. When set to "file" it means that the source data is a path towards a file.
This transformer currently only stores "block blobs"
block blob: 
Block blobs let you upload large blobs efficiently. Block blobs are comprised of blocks, each of which is identified by a block ID. You create or modify a block blob by writing a set of blocks and committing them by their block IDs. Each block can be a different size, up to a maximum of 4 MB, and a block blob can include up to 50,000 blocks. The maximum size of a block blob is therefore slightly more than 195 GB (4 MB X 50,000 blocks). If you are writing a block blob that is no more than 64 MB in size, you can upload it in its entirety with a single write operation
append blob:
An append blob is comprised of blocks and is optimized for append operations. When you modify an append blob, blocks are added to the end of the blob only, via the Append Block operation. Updating or deleting of existing blocks is not supported. Unlike a block blob, an append blob does not expose its block IDs. 
Each block in an append blob can be a different size, up to a maximum of 4 MB, and an append blob can include up to 50,000 blocks. The maximum size of an append blob is therefore slightly more than 195 GB (4 MB X 50,000 blocks).
page blob:
Page blobs are a collection of 512-byte pages optimized for random read and write operations. To create a page blob, you initialize the page blob and specify the maximum size the page blob will grow. To add or update the contents of a page blob, you write a page or pages by specifying an offset and a range that align to 512-byte page boundaries. A write to a page blob can overwrite just one page, some pages, or up to 4 MB of the page blob. Writes to page blobs happen in-place and are immediately committed to the blob. The maximum size for a page blob is 1 TB. 
Request Headers: Additional headers that should be used when sending the request.
Selected attributes will be used to build the headers, example:
If selected attributes are 
Content-Encoding
Content-Type
x-ms-blob-content-disposition
and the feature entering the transformer have these attributes, something like this would be added to the headers used in the request:
x-ms-blob-content-disposition: attachment; filename=thedata.txt;
Content-Type: text/plain; charset=UTF-8
Content-Encoding: UTF-8
See also: https://docs.microsoft.com/en-us/rest/api/storageservices/fileservices/put-blob

Parameters:
- ACCOUNT =
- BLOB_NAME =
- CONTAINER =
- KEY =
- SRC_DATA =
- SRC_TYPE =
- XTRA_HEADERS =
- _PATHNAME =

Input (input)
    -> ParameterFetcher
ParameterFetcher
    ATTR_LIST = _azure_blob_uploader_headers {$(XTRA_HEADERS)}
    -> Tester
Tester
    BOOL_OP = OR
    TEST_CLAUSE = TEST @Value(_azure_blob_uploader_headers) ATTRIBUTE_HAS_VALUE ""
    TEST_MODE = TEST
    PASSED -> StringSearcher
    FAILED -> FetchParamsAttributeCreator
StringSearcher
    CASE = no
    MATCHED_PARTS_ATTR = _azure_blob_uploader_header_attributes
    MATCHED_RESULT_ATTR = _first_match
    REGEXP = (?:^|,)(?=[^"]|(")?)"?((?(1)[^"]*|[^,"]*))"?(?=,|$)
    STRING_TO_SEARCH = @Value(_azure_blob_uploader_headers)
    MATCHED -> FetchParamsAttributeCreator
    NOT_MATCHED -> AttributeRemover_2
FetchParamsAttributeCreator: AttributeCreator
    ATTR_TABLE:
      SET_TO _azure_blob_uploader_storage_account = $(ACCOUNT)
      SET_TO _azure_blob_uploader_key = $(KEY)
      SET_TO _azure_blob_uploader_container = $(CONTAINER)
      SET_TO _azure_blob_uploader_blob_name = $(BLOB_NAME)
      SET_TO _azure_blob_uploader_src_type = $(SRC_TYPE)
      SET_TO _azure_blob_uploader_src_data = $(SRC_DATA)
      SET_TO _pathname = $(_PATHNAME)
    -> AzureBlobStorageConnector
    -> Inspector
AzureBlobStorageConnector
    ACCOUNT_KEY = @Value(_azure_blob_uploader_key)
    ACCOUNT_NAME = @Value(_azure_blob_uploader_storage_account)
    CREDENTIAL_SOURCE = EMBEDDED
    OPERATION_TYPE = Upload
    PARAMETER_SETUP = _FME_SOURCE_TYPE]File]_FME_SOURCE_FILE]@Value(_azure_blob_uploader_src_data)]_FME_SOURCE_FOLDER]<Unused>]_FME_INCLUDE_SUBFOLDERS]<Unused>]_FME_CONTENTS_ONLY]<Unused>]_FME_DATA_TO_UPLOAD]<Unused>]_FME_AZURE_CONTAINER]@Value(_azure_blob_uploader_container)]_FME_UPLOAD_DESTINATION_PATH]@Value(_pathname)]_FME_UPLOAD_ATTR_FILENAME]<Unused>]_FME_HANDLE_EXISTING_FILE]Overwrite]_FME_AZURE_MAX_BLOCK_SIZE]4]_FME_METADATA_GROUP]]_FME_AZURE_CUSTOM_HEADERS]]_FME_SAS_GENERATE]NO]_FME_SAS_PERMISSIONS]<Unused>]_FME_SAS_EXPIRY_TIME]<Unused>]_FME_SAS_IP_RANGE]<Unused>]_FME_SAS_HTTPS]<Unused>]_FME_ATTRIBUTES_TO_ADD]]FME_CONTROLLER_QUERY_FILE]azureblobstorageconnector_deps/Upload.fme
    -> Success (output)
    <REJECTED> -> UUIDGenerator
AzureBlobStorageConnector_2
    ACCOUNT_KEY = @Value(_azure_blob_uploader_key)
    ACCOUNT_NAME = @Value(_azure_blob_uploader_storage_account)
    CREDENTIAL_SOURCE = EMBEDDED
    OPERATION_TYPE = Upload
    PARAMETER_SETUP = _FME_SOURCE_TYPE]File]_FME_SOURCE_FILE]@Value(fileOutput)]_FME_SOURCE_FOLDER]<Unused>]_FME_INCLUDE_SUBFOLDERS]<Unused>]_FME_CONTENTS_ONLY]<Unused>]_FME_DATA_TO_UPLOAD]<Unused>]_FME_AZURE_CONTAINER]@Value(_azure_blob_uploader_container)]_FME_UPLOAD_DESTINATION_PATH]@Value(_pathname)]_FME_UPLOAD_ATTR_FILENAME]<Unused>]_FME_HANDLE_EXISTING_FILE]Overwrite]_FME_AZURE_MAX_BLOCK_SIZE]4]_FME_METADATA_GROUP]]_FME_AZURE_CUSTOM_HEADERS]]_FME_SAS_GENERATE]NO]_FME_SAS_PERMISSIONS]<Unused>]_FME_SAS_EXPIRY_TIME]<Unused>]_FME_SAS_IP_RANGE]<Unused>]_FME_SAS_HTTPS]<Unused>]_FME_ATTRIBUTES_TO_ADD]]FME_CONTROLLER_QUERY_FILE]azureblobstorageconnector_deps/Upload.fme
    -> Success (output)
    <REJECTED> -> Fail (output)
Success (output)
Inspector [off]
AttributeRemover_2
    -> Fail (output)
Fail (output)

Bookmark: If file cannot be uploaded, create a copy with a UUID name and palce it in a temp folder
UUIDGenerator
    UUID_ATTR = _uuid
    -> FileSystemDeleteMoveCopyExist [FileName]
FileSystemDeleteMoveCopyExist
    Action = COPY
    FILEINPUT = @Value(_azure_blob_uploader_src_data)
    FILEOUTPUT = @Value(_pathname)/@Value(_uuid).csv.gz
    Success -> AzureBlobStorageConnector_2

FME custom transformer ConvertImageToDimensionINT8

Parameters:
- FILEID =
- FME_JOBID =
- GRIDCELLSPACING =
- NAME =
- SOURCEFILE =
- __TEMPDIMENSIONLOCATIONPATH =

Raster (input)
    -> ParameterFetcher
ParameterFetcher
    ATTR_LIST = _FME_JOBID $(FME_JOBID)
    -> FilenamePartExtractor_3
FilenamePartExtractor_3
    FULLNAME_ATTR = _source_filename
    SRC_ATTR = @Value(SourceFile)
    -> ExecutionMode
ExecutionMode: TestFilter
    DEFAULT_VALUE = DEBUGGER
    TEST_LIST = "BOOL_OP,OR,COMPOSITE_TEST,""""""1"""""",TEST_CLAUSE,TEST @Value(_FME_JOBID) != -1",FMESERVER
    FMESERVER -> TempPathnameCreator
    DEBUGGER -> AttributeCreator_6
Note: Create temp folder to extract the zip
TempPathnameCreator
    PATHNAME_ATTR = _tempPathName
    -> TempPathnameCreator_2
Note: Create temp folderto place the transformed raster files
TempPathnameCreator_2
    PATHNAME_ATTR = _compressedTempPathName
    -> getMetaDataFromZip [InputZip]
Note: for testing in desktop
AttributeCreator_6
    ATTR_TABLE:
      SET_TO _tempPathName = S:\Common workspace\CrossProjects\Jedi\Bilbomatica\Testing\
      SET_TO _compressedTempPathName = S:\Common workspace\CrossProjects\Jedi\Bilbomatica\temp\
    -> getMetaDataFromZip [InputZip]
Note: Read GeoTiff - file into FME
FeatureReader_2
    ATTR_ACCUM_MODE = Merge Initiator and Result
    ATTR_CONFLICT_RES = Use Result
    COMBINE_GEOM = Use Result
    DATASET = @Value(path_windows)
    FORMAT = GEOTIFF
    GEOTIFF_APPLY_GCPS = NO
    GEOTIFF_FEATURE_TYPE_NAME = FORMAT_NAME
    GEOTIFF_IGNORE_RASTER_TYPE_KEY = No
    GEOTIFF_PREFER_FILE_CS_UNITS = Yes
    GEOTIFF_READER_META_ATTRIBUTES = fme_dataset fme_basename
    GEOTIFF_READ_OFFSETS_IN_CS_UNITS = No
    GEOTIFF_USE_SEARCH_ENVELOPE = NO
    INTERACT = <No Spatial Filter>
    MAX_FEATURES = 1000
    OUTPUT_FEATURES_DISPLAY = Schema and Data Features
    <OTHER> -> RasterPercent_Sampler
    <REJECTED> -> AttributeCreator_3
RasterPercent_Sampler: RasterPercentSampler
    Percentage = 10
    _FILENAME = @Value(_filename)
    -> CoordinateSystemExtractor
    Error -> AttributeCreator_14
CoordinateSystemExtractor
    CRDSYS_ATTR = _coordsys
    -> TestCoordSystem
TestCoordSystem: TestFilter
    DEFAULT_VALUE = Ok
    TEST_LIST:
      "BOOL_OP,AND,COMPOSITE_TEST,""""""1 AND 2"""""",TEST_CLAUSE,TEST @Value(_coordsys) != ETRS89.Europe/EqArea
      TEST @Value(_coordsys) != ETRF89.Europe/EqArea",No ETRS89,"BOOL_OP,OR,COMPOSITE_TEST,""""""1"""""",TEST_CLAUSE,TEST @Value(_coordsys) = """,Empty
    No ETRS89 -> AttributeCreator_10
    Empty -> AttributeCreator_10
    Ok -> RasterPropertyExtractor
RasterPropertyExtractor
    -> AttributeExposer
    <REJECTED> -> AttributeCreator_5
Note: Get CompressionMethod and geotiff_number_of_bits_per_cell (NBITS)
AttributeExposer
    ATTR_LIST = geotiff_compression_method,geotiff_number_of_bits_per_cell
    -> ResolutionTester
ResolutionTester: TestFilter
    DEFAULT_VALUE = ResolutionNoOK
    TEST_LIST:
      "BOOL_OP,AND,COMPOSITE_TEST,""""""1 AND 2"""""",TEST_CLAUSE,TEST @Value(GridCellSpacing) = @Evaluate(@int16(@Value(_spacing_x)))
      TEST @Value(GridCellSpacing) = @int16(@Value(_spacing_y))",ResolutionOK
    ResolutionOK -> NBITS_Tester
    ResolutionNoOK -> AttributeCreator_13
NBITS_Tester: TestFilter
    DEFAULT_VALUE = NBITS
    TEST_LIST = "BOOL_OP,OR,COMPOSITE_TEST,""""""1"""""",TEST_CLAUSE,TEST geotiff_number_of_bits_per_cell ATTRIBUTE_IS_MISSING """,No_NBITS
    No_NBITS -> RasterBandSeparator
    NBITS -> AttributeCreator_12
Note: Split the bands of the raster
RasterBandSeparator
    BAND_INDEX_FIELD = _band_index
    PALETTE_INDEX_FIELD = _palette_index
    RASTER_INDEX_FIELD = _raster_index
    SPLIT_BY_NAME = Band Only
    -> NumBandsTester
    <REJECTED> -> AttributeCreator_7
NumBandsTester: TestFilter
    DEFAULT_VALUE = Multiband
    TEST_LIST = "BOOL_OP,OR,COMPOSITE_TEST,""""""1"""""",TEST_CLAUSE,TEST @Value(_num_bands) = 1",SingleBand
    SingleBand -> RasterBandPropertyExtractor
    Multiband -> AttributeCreator_9
Note: read the properties of each band
RasterBandPropertyExtractor
    -> AttributeRemover
    <REJECTED> -> AttributeCreator_11
AttributeRemover
    REMOVE_ATTRS = GridCellSpacing,__TempDimensionLocationPath,_cell_origin_x,_cell_origin_y,_compressedTempPathName,_coordsys,_dirname,_dirpath,_extension,_inputZipFile,_lower_left_x,_lower_left_y,_lower_right_x,_lower_right_y,_max_x,_max_y,_min_x,_min_y,_num_columns,_num_rows,_origin_x,_origin_y,_palette_index,_raster_index,_rotation_x,_rotation_y,_scanZipInZip,_spacing_x,_spacing_y,_status,_tempPathName,_upper_left_x,_upper_left_y,_upper_right_x,_upper_right_y,action,destinationFolder,fileCounter,fileExtension,fileInput,geotiff_compression_method,path_windows,sourceZipFile,zipFileName,zipSourceFile
    -> AttributeCreator_2
Note: Keep: NoData and band interpreation (int, byte, float etc)
AttributeCreator_2
    ATTR_TABLE:
      SET_TO nodatavalue = @Value(_band{0}.band_nodata)
      SET_TO band_bit_depth = @Value(_band{0}.band_bit_depth)
      SET_TO _band_interpretation = @Value(_band{0}.band_interpretation)
    -> GeometryRemover
Note: Remove geometry as we not interested in it
GeometryRemover
    -> AttributeValueMapper
Note: Convert FME types into MicrosoftSQL types
AttributeValueMapper
    DIRECTION = Forward (Source To Destination)
    LUT = GRAY8,tinyint,GRAY16,smallint,RED8,tinyint,RED16,smallint,GREEN8,tinyint,GREEN16,smallint,BLEU8,tinyint,BLUE16,smallint,ALPHA8,tinyint,APLHA16,smallint,UINT8,tinyint,INT8,smallint,UINT16,int,INT16,smallint,UINT32,int,INT32,int,UINT64,bigint,INT64,bigint,REAL32,float(32),REAL64,float(53)
    SRC = _band_interpretation
    VAL_ATTR = FieldType
    -> AttributeCreator_8
AttributeCreator_8
    ATTR_TABLE:
      SET_TO DimensionName = @Value(Name)
      SET_TO OutputFilename = @Value(SourceFile)
      SET_TO ExcludeValues = FME_CONDITIONAL:DEFAULT_VALUE'-9999'BOOL_OP;AND;COMPOSITE_TEST;1;TEST nodatavalue ATTRIBUTE_HAS_A_VALUE _FME_BLANK_STRING_'@Value(nodatavalue)'FME_NUM_CONDITIONS2___
    -> AttributeKeeper
    -> AttributeRemover_2
AttributeRemover_2
    LIST_ATTRS = _band{} _band{}.band_bit_depth _band{}.band_interpretation _band{}.band_name _band{}.band_nodata _band{}.band_num_palettes _band{}.band_num_tile_columns _band{}.band_num_tile_rows _band{}.band_selected _band{}.palette{} _band{}.palette{}.palette_bit_depth _band{}.palette{}.palette_key_interpretation _band{}.palette{}.palette_name _band{}.palette{}.palette_selected _band{}.palette{}.palette_value_interpretation
    REMOVE_ATTRS = ExcludeValues,FieldType,_band_index,_band_interpretation,_band{0}.band_bit_depth,_band{0}.band_interpretation,_band{0}.band_name,_band{0}.band_nodata,_band{0}.band_num_palettes,_band{0}.band_num_tile_columns,_band{0}.band_num_tile_rows,_band{0}.band_selected,_band{0}.palette{0}.palette_bit_depth,_band{0}.palette{0}.palette_key_interpretation,_band{0}.palette{0}.palette_name,_band{0}.palette{0}.palette_selected,_band{0}.palette{0}.palette_value_interpretation,_num_bands,_rootname,band_bit_depth,fileOutput,geotiff_number_of_bits_per_cell,nodatavalue,numTifFiles,sourceFile
    -> Aggregator
Aggregator
    ACCUM_ATTRS_NAME = Use Attributes From One Feature
    AGGREGATE_TYPE = Homogeneous Collection (If Possible)
    GROUP_BY = DimensionName
    MODE = Geometry - Assemble One Level
    SEP = ,
    AGGREGATE -> OptimisedRaster (output)
OptimisedRaster (output)
AttributeKeeper
    CREATE_BULK_MODE_FEATURES = NO
    KEEP_ATTRS = DimensionName,ExcludeValues,FieldType,FileId,Name,OutputFilename,SourceFile,_FME_JOBID,_filename,numTifFiles,_rootname,ParentZip
    -> Attr_Category
Note: Create attributes for dimension field definition
Attr_Category: AttributeCreator
    ATTR_TABLE:
      SET_TO FileId = @Value(FileId)
      SET_TO FieldName = @Value(_rootname)
      SET_TO Alias = FME_CONDITIONAL:DEFAULT_VALUE'Category_@Value(_rootname)'BOOL_OP;OR;COMPOSITE_TEST;1;TEST @Value(numTifFiles) = Category''FME_NUM_CONDITIONS2___
      SET_TO Title
      SET_TO Description
      SET_TO IgnoreField = 0
    -> CategoryDefinition (output)
CategoryDefinition (output)
AttributeCreator_11
    ATTR_TABLE = SET_TO _error = ERROR: Error extracting band properties
    -> Junction
AttributeCreator_9
    ATTR_TABLE = SET_TO _error = ERROR: Cannot extract properties: Raster is multiband
    -> Junction
AttributeCreator_7
    ATTR_TABLE = SET_TO _error = ERROR: Cannot extract properties: @Value(fme_rejection_message)
    -> Junction
AttributeCreator_12
    ATTR_TABLE = SET_TO _error = ERROR: Cannot extract properties: Raster contains NBITS property
    -> Junction
AttributeCreator_13
    ATTR_TABLE = SET_TO _error = ERROR: Raster must be @Value(GridCellSpacing)x@Value(GridCellSpacing)
    -> Junction
AttributeCreator_5
    ATTR_TABLE = SET_TO _error = ERROR: Cannot extract properties: @Value(fme_rejection_message)
    -> Junction
AttributeCreator_10
    ATTR_TABLE = SET_TO _error = ERROR: No valid Reference System in @Value(_filename) MUST BE EPSG:3035
    -> Junction
Junction
    -> Logger_2
AttributeCreator_14
    ATTR_TABLE = SET_TO _error = @Value(_error)
    -> Logger_2
AttributeCreator_3
    ATTR_TABLE = SET_TO _error = ERROR reading GeoTIFF file:
    -> Logger_2
Inspector [off]
JediLogWritter_startjob_5
    FILEID = 355
    MESSAGESTRING = ERROR1
    MESSAGETYPE = INFO
    OBJECTPROCESSED = Dimension
    SQLServerConn = CubeManager
    TRANSFORMERPATH = $(WORKSPACE_NAME)\OptimiseAndUploadDimensionFile
    -> AttributeCreator_4
Failed (output)

Bookmark: Extract files form Zip file
getMetaDataFromZip
    inputZipFile = @Value(SourceFile)
    scanZipInZip = yes
    -> ExtractFileFromZip
ExtractFileFromZip
    DESTINATIONFOLDER = @Value(_tempPathName)
    SOURCEFILE = @Value(zipFileName)
    ZIPSOURCEFILE = @Value(sourceZipFile)
    SUCCESS -> AttributeCreator
    FAILED -> JediLogWritter_startjob_5

Bookmark: Extract the Path of the files and get the Tif files only
AttributeCreator
    ATTR_TABLE = SET_TO path_windows = @Value(_tempPathName)/@Value(zipFileName)
    -> FilenamePartExtractor
FilenamePartExtractor
    DIRNAME_ATTR = _dirname
    DIRPATH_ATTR = _dirpath
    EXTENSION_ATTR = _extension
    FULLNAME_ATTR = _filename
    ROOTNAME_ATTR = _rootname
    SRC_ATTR = @Value(path_windows)
    -> TestFilter
    -> Inspector
TestFilter
    DEFAULT_VALUE = <UNFILTERED>
    TEST_LIST:
      "BOOL_OP,AND,COMPOSITE_TEST,""""""1 AND 2"""""",TEST_CLAUSE,CASE_INSENSITIVE_TEST @Value(_extension) = tif
      CASE_INSENSITIVE_TEST @Value(zipFileName) NOT_BEGINS_WITH __MACOSX",tif
    tif -> FeatureReader_2 [INITIATOR]

Bookmark: PASS ERROR MESSAGE
AttributeCreator_4
    ATTR_TABLE = SET_TO _error = Failed in unzipping file: @Value(_tempPathName)
    -> Logger_2
Logger_2
    MAXCOORDS = 20
    MAXFEATS = 20
    MESSAGE = @Value(_error)
    LOGGED -> SQLExecutor_Error [INITIATOR]
Note: Cannot read Raster file
SQLExecutor_Error
    COMBINE_ATTRS = Result Attributes Only
    COMBINE_GEOM = Initiator Geometry Only
    DATASET = CubeManager
    FORMAT = MSSQL_ADO
    MSSQL_ADO_COMMAND_TIMEOUT = 30
    MSSQL_ADO_NAMED_CONNECTION = CubeManager
    MSSQL_ADO_QUERY_FEATURE_TYPES_FOR_MERGE_FILTERS = Yes
    SQL_STATEMENT:
      Update dbo.Files
          set ErrorMessages = '@Value(_error)'
      where FileId = @Value(FileId)
    INITIATOR -> AttributeCreator_Error_path
    <REJECTED> -> AttributeCreator_Error_path
AttributeCreator_Error_path
    ATTR_TABLE = SET_TO TransformerPathError = SQLExecutor_Error
    -> Failed (output)

FME custom transformer UploadFilesToHDFS

Parameters:
- DIMENSIONNAME =
- OUTPUTFILENAME =
- _DATASET =

UploadFilesToDBFS (input)
    -> AttributeCreator
AttributeCreator
    ATTR_TABLE = SET_TO destFile = CubeSourceDataFile/@Value(DimensionName)/@Value(OutputFilename)
    -> AzureBlobUploader
    -> AzureBlobStorageConnector [off]
    -> AzureBlobUploader_2
Note: Send SourceFile to Microsoft Azure
AzureBlobUploader [off]
    ACCOUNT = cwsblobstorage01
    BLOB_NAME = @Value(destFile)
    CONTAINER = cwsblob01
    KEY =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
    SRC_DATA = @Value(_dataset)
    SRC_TYPE = FilePath
    Success -> Output (output)
    Fail -> Error (output)
AzureBlobStorageConnector [off]
    ACCOUNT_KEY = @Value(_azure_blob_uploader_key)
    ACCOUNT_NAME = @Value(_azure_blob_uploader_storage_account)
    CREDENTIAL_SOURCE = EMBEDDED
    OPERATION_TYPE = Upload
    PARAMETER_SETUP = _FME_SOURCE_TYPE]File]_FME_SOURCE_FILE]@Value(_azure_blob_uploader_src_data)]_FME_SOURCE_FOLDER]<Unused>]_FME_INCLUDE_SUBFOLDERS]<Unused>]_FME_CONTENTS_ONLY]<Unused>]_FME_DATA_TO_UPLOAD]<Unused>]_FME_AZURE_CONTAINER]@Value(_azure_blob_uploader_container)]_FME_UPLOAD_DESTINATION_PATH]@Value(_azure_blob_uploader_blob_name)]_FME_UPLOAD_ATTR_FILENAME]<Unused>]_FME_HANDLE_EXISTING_FILE]Overwrite]_FME_AZURE_MAX_BLOCK_SIZE]4]_FME_METADATA_GROUP]]_FME_AZURE_CUSTOM_HEADERS]]_FME_SAS_GENERATE]NO]_FME_SAS_PERMISSIONS]<Unused>]_FME_SAS_EXPIRY_TIME]<Unused>]_FME_SAS_IP_RANGE]<Unused>]_FME_SAS_HTTPS]<Unused>]_FME_ATTRIBUTES_TO_ADD]]FME_CONTROLLER_QUERY_FILE]azureblobstorageconnector_deps/Upload.fme
    INITIATOR -> Output (output)
    <REJECTED> -> Error (output)
Note: Send SourceFile to Microsoft Azure
AzureBlobUploader_2
    ACCOUNT = cwsblobstorage01
    BLOB_NAME = @Value(destFile)
    CONTAINER = cwsblob01
    KEY =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
    SRC_DATA = @Value(_dataset)
    SRC_TYPE = FilePath
    _PATHNAME = CubeSourceDataFile/@Value(DimensionName)
    Success -> Output (output)
    Fail -> Error (output)
Output (output)
Error (output)

FME custom transformer getFilesNamesInZip
Retrieve the file and folder names from a zip file. The transformer is not reading the files itself. It just extracts the stored files.

Parameters:
- sourceZipFile =

zipFile (input)
    -> ParameterFetcher
ParameterFetcher
    ATTR_LIST = sourceZipFile {$(sourceZipFile)}
    -> readZipContentPy
Note: Retrieves the files from a .zip file and expose those as features.
readZipContentPy: PythonCaller
    NEW_ATTRIBUTES = _zipFileContent{} numTifFiles
    PYTHONSOURCE:
      import fmeobjects
      # Template Function interface:
      def processFeature(feature):
          pass

      # Template Class Interface:
      class FeatureProcessor(object):
          def __init__(self):
              pass
          def input(self,feature):
              import zipfile
              # get file name form FME
              myzipfile = feature.getAttribute("sourceZipFile")
              # zipfileContent list that we will send back to FME
              _zipFileContent=[]
              _numTiffFiles=0
              # Open zip file.
              try:
                  zz = zipfile.ZipFile(myzipfile)
                  #zz.printdir()
                  for name in zz.infolist():
                      _zipFileContent.append(name.filename)
                      if ( name.filename.endswith('.tif')):
                         _numTiffFiles = _numTiffFiles+1
                  zz.close()
              except:
                  pass
              # send content back to FME as a list
              feature.setAttribute("_zipFileContent{}",_zipFileContent)
              feature.setAttribute("numTifFiles",_numTiffFiles)
              self.pyoutput(feature)
          def close(self):
              pass
    PYTHONSYMBOL = FeatureProcessor
    -> TifFilesInZip
    -> ListExploder
Note: Test how many .tif files in zip
TifFilesInZip: Tester [off]
    BOOL_OP = OR
    COMPOSITE_TEST = 1
    TEST_CLAUSE = TEST @Value(numTifFiles) > 0
    TEST_MODE = TEST
    PASSED -> ListExploder
    FAILED -> NoTifFiles (output)
Note: File names to feature list
ListExploder
    INDEX_ATTR = fileCounter
    LIST_ATTR = _zipFileContent{}
    MODE = List Elements and Original Attributes
    LIST_FOUND -> AttributeRenamer
Files (output)
NoTifFiles (output)

Bookmark: Split Filename and Extension
AttributeRenamer
    ATTR_LIST = _zipFileContent,zipFileName,""
    -> FilenamePartExtractor
Note: Extract file extension
FilenamePartExtractor
    EXTENSION_ATTR = fileExtension
    SRC_ATTR = @Value(zipFileName)
    -> Files (output)

FME custom transformer RasterPercentSampler
Custom transformer to build a new raster that is the parameter% of the size of the original

Parameters:
- Percentage =
- _FILENAME =

Input (input)
    -> RasterResampler
    -> Clipper [CLIPPEE]
Clipper
    BOUNDARY_CASES = Treat as Inside
    CLEANING_TOLERANCE = Automatic
    CLIPPED_ATTR = _clipped
    CLIP_TYPE = Single Clipper
    GROUP_BY = _filename
    LINES_AS_SEGMENTS = No
    MEASURE_TYPE = Continuous
    MISSING_VAL_MODE = Compute
    PRESERVE_CLIPPEE_EXTENTS = No
    VAL_SOURCE = Clippee Only
    INSIDE -> Output (output)
    <REJECTED> -> AttributeCreator_14
Output (output)
Error (output)

Bookmark: Build raster % Sampler
Note: Resampler to build a smaller raster. This way we get teh coordinates in a faster
RasterResampler
    COLUMNS = 10
    INTERPOLATION_TYPE_NAME = Nearest Neighbor
    ROWCOL_OR_CELLSIZE = RowsColumns
    ROWS = 10
    RESAMPLED -> CoordinateExtractor
    <REJECTED> -> AttributeCreator_5
CoordinateExtractor
    IND = 0
    LIST_NAME = _indices
    MODE = All Coordinates
    X_ATTR = _x
    Y_ATTR = _y
    Z_ATTR = _z
    -> 10PercentCoordinates
    <REJECTED> -> AttributeCreator_4
Note: Create xmax and ymax with % of the size of the original
10PercentCoordinates: AttributeCreator
    ATTR_TABLE:
      SET_TO xmin = @Value(_indices{0}.x)
      SET_TO ymin = @Value(_indices{0}.y)
      SET_TO xmax = @Evaluate(@Value(_indices{0}.x) +    (@Value(_indices{2}.x) -@Value(_indices{0}.x))*($(Percentage)/100))
      SET_TO ymax = @Evaluate(@Value(_indices{0}.y) +    (@Value(_indices{2}.y) -@Value(_indices{0}.y))*($(Percentage)/100))
    -> GeometryReplacer
Note: Change area boundaries with the raster % boundaries
GeometryReplacer
    KIND_LONG = OGC Well Known Text
    OGC_WKT_PRECISION_DISPLAY = 64-bit
    REMOVE_ATTRIBUTE = Yes
    SOURCE = POLYGON((@Value(xmin) @Value(ymin),@Value(xmin) @Value(ymax),@Value(xmax) @Value(ymax),@Value(xmax) @Value(ymin),@Value(xmin) @Value(ymin)))
    -> Clipper [CLIPPER]
    <REJECTED> -> AttributeCreator_2

Bookmark: Error Handler
AttributeCreator_14
    ATTR_TABLE = SET_TO _error = @Value(fme_rejection_code)
    -> Error (output)
AttributeCreator_2
    ATTR_TABLE = SET_TO _error = @Value(fme_rejection_code)
    -> Error (output)
AttributeCreator_4
    ATTR_TABLE = SET_TO _error = @Value(fme_rejection_code)
    -> Error (output)
AttributeCreator_5
    ATTR_TABLE = SET_TO _error = @Value(fme_rejection_message)
    -> Error (output)

FME custom transformer getMetaDataFromZip
Extracts the meta information from a zip including the nested zip files one level deep.
Zip file to read: The zipfile you wish to read.
Zip files inside this zip file will be extracted using zipfile1_zipfile2.zip as file name. Be aware that zips using folders who have zip files with the same name might overwrite each other in this version.

Parameters:
- inputZipFile =
- scanZipInZip =

InputZip (input)
    -> ParameterFetcher
ParameterFetcher
    ATTR_LIST = _inputZipFile {$(inputZipFile)} _scanZipInZip {$(scanZipInZip)}
    -> getFilesNamesInZip [zipFile]
EmptyParentZip: AttributeCreator
    ATTR_TABLE = SET_TO ParentZip = FME_NULL_VALUE
    -> Counter
Counter
    CNT_ATTR = fileCounter
    DOMAIN = counter
    SCOPE = Global
    START = 0
    -> Output (output)
Output (output)
ERROR (output)

Bookmark: First level zip file
getFilesNamesInZip
    sourceZipFile = @Value(_inputZipFile)
    Files -> EmptyParentZip
    Files -> TestFilter
    NoTifFiles -> ERROR (output)

Bookmark: Test if content is another zip file
TestFilter
    DEFAULT_VALUE = otherFiles
    TEST_LIST:
      BOOL_OP,AND,COMPOSITE_TEST,<Unused>,TEST_CLAUSE,"TEST @Value(fileExtension) = zip
      TEST @Value(_scanZipInZip) = yes",zip in a zip
    zip in a zip -> rootFolder

Bookmark: Compile a targetFolder for the zip file
Note: We need to extract the zip file, we produce a unique name using the basename of the first zip-file and the filename of the internal zip file.
rootFolder: FilenamePartExtractor
    DIRPATH_ATTR = _dirpath
    ROOTNAME_ATTR = _zipBaseName
    SRC_ATTR = @Value(_inputZipFile)
    -> getRootRame
getRootRame: FilenamePartExtractor
    ROOTNAME_ATTR = _rootname
    SRC_ATTR = @Value(zipFileName)
    -> _newZipFolder
_newZipFolder: AttributeCreator
    ATTR_LIST = _newZipFolder,@Value(_dirpath)@Value(_zipBaseName)_@Value(_rootname),ParentZip,@ReplaceString(@Value(zipFileName),".zip","")
    -> Rem_TempParams
Rem_TempParams: AttributeRemover
    REMOVE_ATTRS = _dirpath,_zipBaseName,_rootname
    -> ExtractFileFromZip

Bookmark: Unzip zip file
ExtractFileFromZip
    DESTINATIONFOLDER = @Value(_newZipFolder)
    SOURCEFILE = @Value(zipFileName)
    ZIPSOURCEFILE = @Value(_inputZipFile)
    SUCCESS -> AttributeCreator
    FAILED -> ERROR (output)
AttributeCreator
    ATTR_LIST = path_windows,@Value(_newZipFolder)\@Value(zipFileName)
    -> AttributeRemover
AttributeRemover
    REMOVE_ATTRS = sourceZipFile,zipFileName,fileCounter,fileExtension,_newZipFolder,zipSourceFile,sourceFile,destinationFolder,action,fileInput,fileOutput,_status
    -> getFilesNames_Zip2 [zipFile]

Bookmark: Get filenames for seccond level zip
getFilesNames_Zip2: getFilesNamesInZip
    sourceZipFile = @Value(path_windows)
    Files -> Counter
    NoTifFiles -> ERROR (output)

FME custom transformer FileSystemDeleteMoveCopyExist_2
This transformer can "move","copy","delete" files. Can as well check if a file "exist" and create or delete folders.
action:The action you like to perform. 
    fileInput: provide the input file path.
    fileOutput: provide the output file path. (Is not used when you delete or test the existance of a file)

Parameters:
- Action =
- FILEINPUT =
- FILEOUTPUT =

FileName (input)
    -> ParameterFetcher
ParameterFetcher
    ATTR_LIST = action {$(Action)} fileInput {$(FILEINPUT)} fileOutput {$(FILEOUTPUT)}
    -> PythonCaller
PythonCaller
    NEW_ATTRIBUTES = "_status "
    PYTHONSOURCE:
      import fmeobjects
      # Template Function interface:
      def processFeature(feature):
          pass

      # Template Class Interface:
      class FeatureProcessor(object):
          def __init__(self):
              pass
          def input(self,feature):
              import os,shutil
              try:
                  # define and get parameters
                  self._status=''
                  self._fileInput = feature.getAttribute('fileInput')
                  self._fileOutput = feature.getAttribute('fileOutput')
                  self._action = feature.getAttribute('action')

                  # When action is "delete"
                  if (self._action.upper() == "DELETE"):
                      if os.path.exists(self._fileInput):
                          os.remove(self._fileInput)
                          self._status='deleted'
                      else:
                          self._status='notexist:' + self._fileInput

                  # When action is "delete folder"
                  if (self._action.upper() == "RMDIR"):
                      if os.path.exists(self._fileInput):
                          shutil.rmtree(self._fileInput)
                          self._status='deleted'
                      else:
                          self._status='notexist:' + self._fileInput

                  # When action is "copy"
                  if (self._action.upper() == "COPY"):
                      if os.path.exists(self._fileInput):
                          shutil.copy(self._fileInput,self._fileOutput)
                          self._status='copied'
                      else:
                          self._status='notexist:' + self._fileInput

                  # When action is "move"
                  if (self._action.upper() == "MOVE"):
                      if os.path.exists(self._fileInput):
                          shutil.move(self._fileInput,self._fileOutput)
                          self._status='moved'
                      else:
                          self._status='notexist:' + self._fileInput

                  # When action is " mkdir"
                  if (self._action.upper() == "MKDIR"):
                      if os.path.exists(self._fileInput):
                          self._status='created'
                      else:
                          os.makedirs(self._fileInput)
                          self._status='created'

                  # When action is "exist"
                  if (self._action.upper() == "EXIST"):
                      if os.path.exists(self._fileInput):
                          self._status='exist'
                      else:
                          self._status='notexist:' + self._fileInput
              except:
                  self._status='error'

              feature.setAttribute('_status',self._status)
              self.pyoutput(feature)
          def close(self):
              pass
    PYTHONSYMBOL = FeatureProcessor
    -> TestFilter
TestFilter
    DEFAULT_VALUE = Failed
    TEST_LIST:
      BOOL_OP,OR,COMPOSITE_TEST,<Unused>,TEST_CLAUSE,"TEST @Value(_status) = deleted
      TEST @Value(_status) = copied
      TEST @Value(_status) = moved
      TEST @Value(_status) = exist
      TEST @Value(_status) = created",Success,BOOL_OP,OR,COMPOSITE_TEST,<Unused>,TEST_CLAUSE,"TEST @Value(_status) BEGINS_WITH notexist:",DoesNotExist
    Success -> Success (output)
    DoesNotExist -> NotFound (output)
    Failed -> Failed (output)
Success (output)
NotFound (output)
Failed (output)
