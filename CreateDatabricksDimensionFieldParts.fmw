FME workspace CreateDatabricksDimensionFieldParts.fmw

Parameters:
- DestDataset_MSSQL_JDBC_NONSPATIAL =
- FileId =

Writers:
- MSSQL_JDBC_NONSPATIAL_1: MSSQL_JDBC_NONSPATIAL to $(DestDataset_MSSQL_JDBC_NONSPATIAL)

Creator
    GEOMTYPE = Geometry Object
    NUM = 1
    CREATED -> Junction_11 [off]
    CREATED -> FME_ID_creator
Junction_11
    -> SQLExecutor_5 [INITIATOR]
SQLExecutor_5
    COMBINE_ATTRS = Result Attributes Only
    COMBINE_GEOM = Initiator Geometry Only
    DATASET = CubeManager
    EXPOSED_ATTRIBUTE_LIST = FileId SQLDWTableName
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = CubeManager
    MSSQL_ADO_QUERY_FEATURE_TYPES_FOR_MERGE_FILTERS = Yes
    SQL_STATEMENT:
      /****** Script for SelectTopNRows command from SSMS  ******/
      SELECT  [FileId]
            ,SQLDWTableName
        FROM [CubeManager].[dbo].[Files]
        where fileid= $(FileId)
    RESULT -> AttributeCreator_7
JediLogWritter_startjob_4
    FILEID = $(FileId)
    MESSAGESTRING = Calling RunDatabricksJob
    MESSAGETYPE = INFO
    OBJECTPROCESSED = Dimension
    SQLServerConn = CubeManager
    TRANSFORMERPATH = $(WORKSPACE_NAME)\CreateDtabricksDimension
    -> SQLExecutor_2 [INITIATOR]
Note: Check if there is a RunID in the Database
SQLExecutor_2
    ATTR_IGNORE_NULLS = No
    COMBINE_ATTRS = Keep Initiator Attributes if Conflict
    COMBINE_GEOM = Initiator Geometry Only
    DATASET = CubeManager
    EXPOSED_ATTRIBUTE_LIST = ExecutingRunId
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = CubeManager
    MSSQL_ADO_QUERY_FEATURE_TYPES_FOR_MERGE_FILTERS = Yes
    SQL_STATEMENT:
      SELECT [dbo].[Files].[runId] as ExecutingRunId
      FROM [dbo].[Files]
      WHERE [dbo].[Files].[FileId] = @Value(FileId)
    RESULT -> TestFilter_2
TestFilter_2
    DEFAULT_VALUE = <UNFILTERED>
    TEST_LIST = "BOOL_OP,OR,COMPOSITE_TEST,""""""1"""""",TEST_CLAUSE,TEST @Value(ExecutingRunId) != 0",DatabricksRunning,"BOOL_OP,OR,COMPOSITE_TEST,""""""1"""""",TEST_CLAUSE,TEST @Value(ExecutingRunId) = 0",DatabricksNotRunning
    DatabricksRunning -> CheckRunStatus [DatabrickAPICallerInput]
    DatabricksNotRunning -> CallProcessCubeJob [DatabrickAPICallerInput]
CallProcessCubeJob: DatabricksAPICaller
    COMMAND = run-now
    DOMAIN = northeurope.azuredatabricks.net
    JOBID = 22
    METHOD = POST
    PARAMETER = "Dimension_Name":"@Value(SQLDWTableName)","SourceFile": "@Value(AzureSourceFile)","FilesToCheck": "@Value(FilesToCheck)" ,"Target_Resolution": @Value(GridTypeScale)
    TOKEN =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
    CallDatabricksJob_Output -> AttributeRemover
AttributeRemover
    REMOVE_ATTRS = ExecutingRunId
    -> testRunJobError
Note: Check if the Job started correctly
testRunJobError: Tester
    BOOL_OP = OR
    COMPOSITE_TEST = 1 OR 2
    TEST_CLAUSE:
      TEST @Value(RunId) = 0
      TEST RunId ATTRIBUTE_IS_MISSING ""
    TEST_MODE = TEST
    PASSED -> JediLogWritter_startjob_2
    FAILED -> JediLogWritter_startjob_3
JediLogWritter_startjob_2
    FILEID = $(FileId)
    MESSAGESTRING = RunDatabricksJobError: @Value(error)
    MESSAGETYPE = ERROR
    OBJECTPROCESSED = Dimension
    SQLServerConn = CubeManager
    TRANSFORMERPATH = $(WORKSPACE_NAME)\CreateDtabricksDimension
    -> ErrorRunningJob
ErrorRunningJob: AttributeCreator
    ATTR_TABLE:
      SET_TO MessageString = Error running CreateDataFrame job: @Value(error)
      SET_TO MessageType = ERROR
    -> Junction_2
Note: SQLExecutor_ErrorWriter : Initiator
Junction_2
    -> Junction_3
JediLogWritter_startjob_3
    FILEID = $(FileId)
    MESSAGESTRING = RunDatabricksJobStarted
    MESSAGETYPE = INFO
    OBJECTPROCESSED = Dimension
    SQLServerConn = CubeManager
    TRANSFORMERPATH = $(WORKSPACE_NAME)\CreateDtabricksDimension
    -> JobStartTimer
Note: In order to checkhow long it takes tp start the cluster
JobStartTimer: AttributeCreator
    ATTR_TABLE = SET_TO StartTime = @DateTimeNow()
    -> SQLExecutor_8 [INITIATOR]
Note: Inserts the RunID in DB to inform that there is a running job in Databricks
SQLExecutor_8
    ATTR_IGNORE_NULLS = No
    COMBINE_ATTRS = Keep Initiator Attributes if Conflict
    COMBINE_GEOM = Initiator Geometry Only
    DATASET = CubeManager
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = CubeManager
    MSSQL_ADO_QUERY_FEATURE_TYPES_FOR_MERGE_FILTERS = Yes
    SQL_STATEMENT:
      update [dbo].[Files]
          set [runId] = @Value(RunId)
      where FileId = @Value(FileId)
    INITIATOR -> WaitUntilDatabtricksJobCompleted [CheckJobStatus_Input]
Note: Wait until Dtabricks completes or times out to start the cliuster
WaitUntilDatabtricksJobCompleted
    MINUTESTOTIMEOUT = 20
    RUNID = @Value(RunId)
    STARTTIME = @Value(StartTime)
    TestFilter_TERMINATED -> JediLogWritter_startjob_6
JediLogWritter_startjob_6
    FILEID = $(FileId)
    MESSAGESTRING = Databricks job completed
    MESSAGETYPE = INFO
    OBJECTPROCESSED = Dimension
    SQLServerConn = CubeManager
    TRANSFORMERPATH = $(WORKSPACE_NAME)\CreateDatabricksDimension
    -> TestJobSuccess
TestJobSuccess: Tester
    BOOL_OP = OR
    COMPOSITE_TEST = 1
    TEST_CLAUSE = TEST @Value(noError) = 1
    TEST_MODE = TEST
    PASSED -> SQLExecutor_3 [INITIATOR]
    PASSED -> AttributeCreator_3
    FAILED -> AttributeCreator_28
AttributeCreator_7
    ATTR_TABLE = SET_TO FileId = $(FileId)
    -> DeleteDimensionStats [Initiator]
DeleteDimensionStats
    FILEID = @Value(FileId)
    SQLDWTABLENAME = @Value(SQLDWTableName)
    fields = @Value(fields)
    -> FeatureReader [INITIATOR]
ProcessCompletedSuccessfully: AttributeCreator
    ATTR_TABLE:
      SET_TO TransformerPath = STATUSFLAG_SUCCESS
      SET_TO MessageString = Tell database that we succeeded.
      SET_TO MessageType = INFO
    -> Junction_7
Note: INFO
Junction_7
    -> Junction_6
ProcessCompletedWithErrors: AttributeCreator
    ATTR_TABLE:
      SET_TO TransformerPath = STATUSFLAG/SUCCESS
      SET_TO MessageString = Error: @Value(_reader_error).
        WorkSpace: $(WORKSPACE_NAME)
        Transformer name: SQLExecutor_3

      SET_TO MessageType = ERROR
    -> Junction_5
Note: ERROR
Junction_5
    -> Junction_3
JediLogWritter_startjob_10
    FILEID = $(FileId)
    MESSAGESTRING = @Value(MessageString)
    MESSAGETYPE = ERROR
    OBJECTPROCESSED = Dimension
    SQLServerConn = CubeManager
    TRANSFORMERPATH = $(WORKSPACE_NAME)\CreateDatabricksDimension
    -> Junction_3
Initial_SQL_Failed: Terminator
    MESSAGE = Translation Terminated

Bookmark: Tell DB we are executing the job
FME_ID_creator: AttributeCreator
    ATTR_TABLE:
      SET_TO _FME_JOB_ID = FME_CONDITIONAL:DEFAULT_VALUE'$(FME_JOB_ID)'BOOL_OP;AND;COMPOSITE_TEST;<Unused>;TEST $(FME_JOB_ID) ATTRIBUTE_IS_MISSING _FME_BLANK_STRING_;TEST $(FME_JOB_ID) NOT_ATTRIBUTE_HAS_VALUE _FME_BLANK_STRING_'-1'FME_NUM_CONDITIONS2___
      SET_TO FileId = $(FileId)
    -> SQLExecutor [INITIATOR]
Note: Reset the database and provide the job_id so log information can be found easily.
SQLExecutor
    COMBINE_ATTRS = Result Attributes Only
    COMBINE_GEOM = Initiator Geometry Only
    DATASET = CubeManager
    FORMAT = MSSQL_ADO
    MSSQL_ADO_COMMAND_TIMEOUT = 30
    MSSQL_ADO_CREATE_FEATURE_TABLES_FROM_DATA = Yes
    MSSQL_ADO_NAMED_CONNECTION = CubeManager
    MSSQL_ADO_QUERY_FEATURE_TYPES_FOR_MERGE_FILTERS = Yes
    SQL_STATEMENT:
      UPDATE dbo.Files
          set
              DimensionFile= NULL,
              AzureDimensionFile = NULL,
              DimensionFileCreated = NULL,
              FMEJobIdDimensionProcess = @Value(_FME_JOB_ID),
              FMEJobIdDimensionProcessStatus=0,
              AzureDimensionUploaded = NULL,
              FMEJobIdDimensionUploaded = @Value(_FME_JOB_ID),
              FMEJobIdDimensionUploadedStatus = 0,
              StatusPercentage =25,
              FMEJobIdValidator = @Value(_FME_JOB_ID),
              FMEJobIdSQLDWCreated = @Value(_FME_JOB_ID),
              FMEJobIdSQLDWCreatedStatus=0,
              TotalRecords=0,
              TotalDuplicates=0
      WHERE FileId = @Value(FileId)
    INITIATOR -> JediLogWritter_startjob
    <REJECTED> -> Initial_SQL_Failed
JediLogWritter_startjob
    FILEID = $(FileId)
    MESSAGESTRING = Conversion started
    MESSAGETYPE = INFO
    OBJECTPROCESSED = Dimension
    SQLServerConn = CubeManager
    TRANSFORMERPATH = $(WORKSPACE_NAME)\CreateDtabricksDimension
    -> GetMetaInfo [INITIATOR]

Bookmark: Retrieve details from DB
Note: Get info from CubeManager database.
GetMetaInfo: SQLExecutor
    COMBINE_ATTRS = Keep Result Attributes if Conflict
    COMBINE_GEOM = Initiator Geometry Only
    DATASET = CubeManager
    EXPOSED_ATTRIBUTE_LIST = AzureDimensionFile AzureSourceFile DimName FieldName FieldType FileDay FileMonth FileYear GridTypeName GridTypeScale SourceFile SQLDWTableName FieldId
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = CubeManager
    MSSQL_ADO_QUERY_FEATURE_TYPES_FOR_MERGE_FILTERS = Yes
    SQL_STATEMENT:
      Select
      [CubeDimensions].[Name] as DimName
      ,[SourceFile]
      ,[AzureSourceFile]
       ,dbo.[Files].[AzureDimensionFile] as AzureDimensionFile

      , concat('D_', [CubeDimensions].[Name],'_', files.fileid,'_',DATEPART(year,dbo.[Files].[SourceFileReceived]),DATEPART(month,dbo.[Files].[SourceFileReceived]), DATEPART(day,dbo.[Files].[SourceFileReceived]),'_', dbo.[GridTypes].name ) as SQLDWTableName
      , DATEPART(year,dbo.[Files].[SourceFileReceived]) as FileYear
      , DATEPART(month,dbo.[Files].[SourceFileReceived]) as FileMonth
      , DATEPART(day,dbo.[Files].[SourceFileReceived]) as FileDay
      , dbo.[Fields].FieldName as FieldName
      , CASE WHEN CHARINDEX('float',LOWER(dbo.[Fields].FieldType) ) > 0 then 2
      			ELSE 1
      	END  as FieldType
      , dbo.[GridTypes].name as GridTypeName
      , dbo.[GridTypes].XCellSpacing as GridTypeScale
      ,FieldId
       from dbo.[CubeDimensions]
       inner join dbo.[Files] on dbo.[CubeDimensions].CubeDimensionId = dbo.[Files].CubeDimensionId
       inner join dbo.[Fields] on dbo.[Files].FileId = dbo.[Fields].FileId and dbo.[Fields].FieldOrder is not null
      inner join dbo.[GridTypes] on dbo.[GridTypes].[GridTypeId] = dbo.[CubeDimensions].[GridTypeId]
      inner join dbo.[DimensionConverters] on dbo.[DimensionConverters].[Name] = dbo.[CubeDimensions].[FMEConversionProcess]
      where  files.fileid= @Value(FileId)
      and IgnoreField =0  and FieldName not IN('x','y','gid')
      and Deprecated =0
    RESULT -> CreateFieldParts
    <REJECTED> -> Initial_SQL_Failed

Bookmark: COMPILE FIELDS AND CREATE PARAMETERS FOR DATABRICKS JOB
Note: FieldName should be used at this stage. / If an Alias is set as 'GridNum' we should change it to that FieldName.
CreateFieldParts
    FIELDID = @Value(FieldId)
    -> CreateJsonItem
CreateJsonItem: AttributeCreator
    ATTR_TABLE = SET_TO JsonFile = {"FieldName":"@Value(FieldName)","Files":[@Value(FieldParts)],"BitDepth": @Value(FieldType)}
    -> Aggregator
Aggregator
    ACCUM_ATTRS_NAME = Use Attributes From One Feature
    AGGREGATE_TYPE = Homogeneous Collection (If Possible)
    CONCAT_ATTRS = JsonFile
    GROUP_BY = AzureSourceFile
    MODE = Geometry - Assemble One Level
    SEP = ,
    AGGREGATE -> StringReplacer
StringReplacer
    CASE = NO
    FIND_TEXT = \
    NO_MATCH = _FME_NO_OP_
    REGEXP = NO
    REPLACE_TEXT = \\
    SRC_ATTRS = SourceFile
    -> TempPathnameCreator
Note: Create temp folder to save the json file
TempPathnameCreator
    PATHNAME_ATTR = _tempPathName
    -> UUIDGenerator
UUIDGenerator
    UUID_ATTR = fileUUID
    -> AttributeCreator
AttributeCreator
    ATTR_TABLE = SET_TO text_line = [@Value(JsonFile)]
    -> AttributeFileWriter
AttributeFileWriter
    CHAR_ENCODING = utf-8
    FILE_NAME = @Value(_tempPathName)/@Value(fileUUID).json
    OVERWRITE_FILE = Overwrite file
    SOURCE_ATTR = text_line
    -> UploadFilesToAzure [UploadFilesToDBFS]
Note: Upload zipped file to Azure Blob Storage
UploadFilesToAzure: UploadFilesToHDFS
    OUTPUTFILENAME = @Value(fileUUID).json
    _DATASET = @Value(_tempPathName)/@Value(fileUUID).json
    -> CreateTableNames
Note: Create Table Name / D_<Dimension Name>_<FileId>_<Date>_External / D_<Dimension Name>_<FileId>_<Date>_<GridTypeName> / D_<Dimension Name>_<FileId>_<Date>_<GridTypeName>_Temp
CreateTableNames: AttributeCreator
    ATTR_TABLE:
      SET_TO DWTableName = FME_CONDITIONAL:DEFAULT_VALUE'@Value(SQLDWTableName)'BOOL_OP;OR;COMPOSITE_TEST;1;TEST SQLDWTableName ATTRIBUTE_VALUE_NULL _FME_BLANK_STRING_'@Value(DimName)_@Value(FileId)_@Value(FileYear)@Value(FileMonth)@Value(FileDay)_@Value(GridTypeName)'FME_NUM_CONDITIONS2___
      SET_TO FilesToCheck = CubeSourceDataFile/@Value(fileUUID).json
    -> JediLogWritter_startjob_4

Bookmark: Check the run status of the cube in databricks
CheckRunStatus: DatabricksAPICaller
    COMMAND = runs/get-output
    DOMAIN = northeurope.azuredatabricks.net
    METHOD = GET
    RUNID = @Value(ExecutingRunId)
    TOKEN =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
    CallDatabricksJob_Output -> TestJobStatus
TestJobStatus: TestFilter
    DEFAULT_VALUE = <UNFILTERED>
    TEST_LIST = "BOOL_OP,OR,COMPOSITE_TEST,""""""1"""""",TEST_CLAUSE,TEST @Value(status) = PENDING",PENDING,"BOOL_OP,OR,COMPOSITE_TEST,""""""1"""""",TEST_CLAUSE,TEST @Value(status) = RUNNING",RUNNING,"BOOL_OP,OR,COMPOSITE_TEST,""""""1"""""",TEST_CLAUSE,TEST @Value(status) = TERMINATING",TERMINATING,"BOOL_OP,OR,COMPOSITE_TEST,""""""1"""""",TEST_CLAUSE,TEST @Value(status) = TERMINATED",TERMINATED
    PENDING -> CancelRun [DatabrickAPICallerInput]
    RUNNING -> CancelRun [DatabrickAPICallerInput]
    TERMINATING -> CancelRun [DatabrickAPICallerInput]
    TERMINATED -> CallProcessCubeJob [DatabrickAPICallerInput]
    <UNFILTERED> -> CallProcessCubeJob [DatabrickAPICallerInput]
CancelRun: DatabricksAPICaller
    COMMAND = runs/cancel
    DOMAIN = northeurope.azuredatabricks.net
    METHOD = POST
    RUNID = @Value(ExecutingRunId)
    TOKEN =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
    CallDatabricksJob_Output -> CallProcessCubeJob [DatabrickAPICallerInput]

Bookmark: STATUSFLAG SUCCESS
Note: Tell database that we succeeded.
SQLExecutor_3
    COMBINE_ATTRS = Result Attributes Only
    COMBINE_GEOM = Initiator Geometry Only
    DATASET = CubeManager
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = CubeManager
    MSSQL_ADO_QUERY_FEATURE_TYPES_FOR_MERGE_FILTERS = Yes
    SQL_STATEMENT:
      UPDATE dbo.Files
          set ErrorMessages = '',
              DimensionFileCreated = getdate(),
              FMEJobIdDimensionProcessStatus=1,
              DimensionFile= NULL,
              AzureDimensionFile = 'Dimensions/@Value(DWTableName)',
              AzureDimensionUploaded = getdate(),
              FMEJobIdDimensionUploadedStatus = 1,
              StatusPercentage =100,
              FMEJobIdSQLDWCreatedStatus=1,
              SQLDWTableName = '@Value(DWTableName)',
              SQLDWTableNameCreated = getdate(),
              TotalRecords=@Value(num_records),
              TotalDuplicates= @Value(has_overlaps),
              runId = 0
      WHERE FileId = @Value(FileId)
    INITIATOR -> ProcessCompletedSuccessfully
    INITIATOR -> SQLExecutor_4 [INITIATOR]
    INITIATOR -> JediLogWritter_startjob_8
    <REJECTED> -> ProcessCompletedWithErrors

Bookmark: Process statistics
JediLogWritter_startjob_8
    FILEID = $(FileId)
    MESSAGESTRING = Calling RunDatabricksJob CreateStatistocs
    MESSAGETYPE = INFO
    OBJECTPROCESSED = Dimension
    SQLServerConn = CubeManager
    TRANSFORMERPATH = $(WORKSPACE_NAME)\CreateDatabricksDimension
    -> CallProcessCubeJob_CreateStatistics [DatabrickAPICallerInput]
CallProcessCubeJob_CreateStatistics: DatabricksAPICaller
    COMMAND = run-now
    DOMAIN = northeurope.azuredatabricks.net
    JOBID = 18
    METHOD = POST
    PARAMETER = "EntityName":"jedi_dimensions.@Value(SQLDWTableName)"
    TOKEN =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
    CallDatabricksJob_Output -> testRunJobError_2
Note: Check if the Job started correctly
testRunJobError_2: Tester
    BOOL_OP = OR
    COMPOSITE_TEST = 1 OR 2
    TEST_CLAUSE:
      TEST RunId ATTRIBUTE_IS_MISSING ""
      TEST @Value(RunId) = 0
    TEST_MODE = TEST
    PASSED -> JediLogWritter_startjob_5
    FAILED -> JediLogWritter_startjob_7
JediLogWritter_startjob_5
    FILEID = $(FileId)
    MESSAGESTRING = RunDatabricksJobError: @Value(error)
    MESSAGETYPE = ERROR
    OBJECTPROCESSED = Dimension
    SQLServerConn = CubeManager
    TRANSFORMERPATH = $(WORKSPACE_NAME)\CreateDtabricksDimension
    -> ErrorRunningJob_2
ErrorRunningJob_2: AttributeCreator
    ATTR_TABLE = SET_TO ErrorString = Error running CreateDataFrame job: @Value(error)
JediLogWritter_startjob_7
    FILEID = $(FileId)
    MESSAGESTRING = RunDatabricksJobStarted
    MESSAGETYPE = INFO
    OBJECTPROCESSED = Dimension
    SQLServerConn = CubeManager
    TRANSFORMERPATH = $(WORKSPACE_NAME)\CreateDtabricksDimension
    -> JobStartTimer_2
Note: In order to checkhow long it takes tp start the cluster
JobStartTimer_2: AttributeCreator
    ATTR_TABLE = SET_TO StartTime = @DateTimeNow()
    -> WaitUntilDatabtricksJobCompleted_2 [CheckJobStatus_Input]
Note: Wait until Dtabricks completes or times out to start the cliuster
WaitUntilDatabtricksJobCompleted_2
    MINUTESTOTIMEOUT = 20
    RUNID = @Value(RunId)
    STARTTIME = @Value(StartTime)
    TestFilter_TERMINATED -> TestJobSuccess_2
    TestFilter_TERMINATED -> JediLogWritter_startjob_9
TestJobSuccess_2: Tester
    BOOL_OP = OR
    COMPOSITE_TEST = 1
    TEST_CLAUSE = TEST @Value(noError) = 1
    TEST_MODE = TEST
    PASSED -> AttributeCreator_7
JediLogWritter_startjob_9
    FILEID = $(FileId)
    MESSAGESTRING = Databricks job completed
    MESSAGETYPE = INFO
    OBJECTPROCESSED = Dimension
    SQLServerConn = CubeManager
    TRANSFORMERPATH = $(WORKSPACE_NAME)\CreateDatabricksDimension

Bookmark: Download and parse JSON from BlobStorage
FeatureReader
    ATTR_ACCUM_MODE = Only Use Result
    COMBINE_GEOM = Use Result
    DATASET = https://cwsblobstorage01.blob.core.windows.net/cwsblob01/statistics/@Value(SQLDWTableName).json
    FORMAT = JSON
    JSON_DECODE_TEXT_STRINGS = Yes
    JSON_FEATURE_TYPE_KEY = json_featuretype
    JSON_FLATTEN_MODE = ALL_LEVELS
    JSON_GEOMETRY_FORMAT = None
    JSON_SAVE_FRAGMENTS = NO
    JSON_SCAN_MODE = AUTO
    JSON_USE_BASENAME_AS_DEFAULT_FEATURE_TYPE = No
    JSON_USE_SEARCH_ENVELOPE = NO
    OUTPUT_FEATURES_DISPLAY = Schema and Data Features
    <OTHER> -> AttributeExposer
    INITIATOR -> AttributeCreator_6
    <REJECTED> -> JediLogWritter_startjob_15
AttributeExposer
    ATTR_LIST = fieldname,fieldValue,grouporder,TotalRecord
    -> AttributeCreator_2
AttributeCreator_2
    ATTR_TABLE:
      SET_TO FieldName = @Value(fieldname)
      SET_TO FieldValue = @Value(fieldValue)
      SET_TO GroupOrder = @Value(grouporder)
      SET_TO TotalRecords = @Value(TotalRecord)
    -> AttributeKeeper_6
AttributeKeeper_6
    CREATE_BULK_MODE_FEATURES = NO
    KEEP_ATTRS = FieldName,FieldValue,GroupOrder,TotalRecords,FileId
    -> ParameterFetcher

Bookmark: Field Statistcis
ParameterFetcher
    ATTR_LIST = FileId $(FileId)
    -> FieldStatistics (writer MSSQL_JDBC_NONSPATIAL_1)
FieldStatistics (writer MSSQL_JDBC_NONSPATIAL_1)
    attributes: FileId integer, FieldName varchar(50), FieldValue varchar(500), TotalRecords integer, GroupOrder integer
JediLogWritter_startjob_15
    FILEID = $(FileId)
    MESSAGESTRING = JSON with stats doesn't exist
    MESSAGETYPE = WARNING
    OBJECTPROCESSED = Cube
    SQLServerConn = CubeManager
    TRANSFORMERPATH = $(WORKSPACE_NAME)\CreateDatabricksDimension

Bookmark: Delete JSON from BlobStorage once read
AttributeCreator_6
    ATTR_TABLE = SET_TO JSONPathInBlobStorage = statistics/@Value(SQLDWTableName).json
    -> AzureBlobStorageConnector
AzureBlobStorageConnector
    CREDENTIAL_SOURCE = WEBCONN
    OPERATION_TYPE = Delete
    PARAMETER_SETUP = _FME_AZURE_CONTAINER]cwsblob01]_FME_FILEID]@Value(JSONPathInBlobStorage)]FME_CONTROLLER_QUERY_FILE]azureblobstorageconnector_deps/Delete.fme
    _FME_AZURE_CONNECTION = JEDI Azure Storage Esparza

Bookmark: Update event log and UpdatedDate
SQLExecutor_4
    COMBINE_ATTRS = Result Attributes Only
    COMBINE_GEOM = Initiator Geometry Only
    DATASET = CubeManager
    FORMAT = MSSQL_ADO
    MSSQL_ADO_COMMAND_TIMEOUT = 30
    MSSQL_ADO_CREATE_FEATURE_TABLES_FROM_DATA = Yes
    MSSQL_ADO_NAMED_CONNECTION = CubeManager
    MSSQL_ADO_QUERY_FEATURE_TYPES_FOR_MERGE_FILTERS = Yes
    SQL_STATEMENT:
      	declare @dimId int
      	select @dimId = CubeDimensionId from Files where FileId= @Value(FileId)

      	update CubeDimensions
      	set lastupdated= GetDate() where CubeDimensionId= @dimId

      	insert into EventLog (DateTime,[Username],[EntityType],[EntityId],[FileId],[Operation]  )
      	values (
      		getdate(),
      		'FME',
      		'Dimension',
      		@dimId,
      		@Value(FileId),
      		'Updated')

Bookmark: CREATE DATABRICKS EXECUTION LOGS
AttributeCreator_3
    ATTR_TABLE:
      SET_TO TransformerPath = RUN DATABRICKS NOTEBOOK
      SET_TO MessageString = CREATEDATAFRAME notebook succeeded
      SET_TO MessageType = INFO
    -> Junction_8
Note: INFO
Junction_8
    -> Junction_6
AttributeCreator_28
    ATTR_TABLE:
      SET_TO TransformerPath = RUN DATABRICKS CREATEDATAFRAME NOTEBOOK
      SET_TO MessageString = Error Running CREATEDATAFRAME notebook
        RunId:@Value(RunId) Cmd:@Value(cmd) Error: @Value(error)
        WorkSpace: $(WORKSPACE_NAME)

      SET_TO MessageType = ERROR
    -> Junction
Note: ERROR
Junction
    -> JediLogWritter_startjob_10

Bookmark: WRITE ERROR IN DB
Junction_3
    -> SQLExecutor_WriteErrorMessage [INITIATOR]
SQLExecutor_WriteErrorMessage
    COMBINE_ATTRS = Result Attributes Only
    COMBINE_GEOM = Initiator Geometry Only
    DATASET = CubeManager
    FORMAT = MSSQL_ADO
    MSSQL_ADO_COMMAND_TIMEOUT = 30
    MSSQL_ADO_CREATE_FEATURE_TABLES_FROM_DATA = Yes
    MSSQL_ADO_NAMED_CONNECTION = CubeManager
    MSSQL_ADO_QUERY_FEATURE_TYPES_FOR_MERGE_FILTERS = Yes
    SQL_STATEMENT:
      Update dbo.Files
          set ErrorMessages = '@Value(MessageString)'
      where FileId =@Value(FileId)
    INITIATOR -> AttributeCreator_5
    <REJECTED> -> AttributeCreator_4
AttributeCreator_5
    ATTR_TABLE:
      SET_TO TransformerPath = WRITE ERROR IN DB
      SET_TO MessageString = @Value(cmd)
    -> Junction_10
Note: INFO
Junction_10
    -> Junction_4
AttributeCreator_4
    ATTR_TABLE:
      SET_TO TransformerPath = WRITE ERROR IN DB
      SET_TO MessageString = Error Running WRITE ERROR IN DB notebook
        @Value(cmd): @Value(error)
        WorkSpace: $(WORKSPACE_NAME)
    -> Junction_9
Note: ERROR
Junction_9
    -> Junction_6

Bookmark: WRITE LOGS
Note: ERROR
Junction_4
    -> AttributeCreator_INFO_2
AttributeCreator_INFO_2
    ATTR_TABLE = SET_TO MessageType = FME_CONDITIONAL:DEFAULT_VALUE'@Value(MessageType)'BOOL_OP;OR;COMPOSITE_TEST;1;TEST MessageType ATTRIBUTE_VALUE_NULL _FME_BLANK_STRING_'INFO'FME_NUM_CONDITIONS2___
    -> AttributeKeeper_2
Note: INFO
Junction_6
    -> AttributeCreator_ERROR_2
AttributeCreator_ERROR_2
    ATTR_TABLE = SET_TO MessageType = ERROR
    -> AttributeKeeper_2
AttributeKeeper_2
    CREATE_BULK_MODE_FEATURES = No
    KEEP_ATTRS = MessageType,TransformerPath,MessageString,FileId
    -> Tester
Tester
    BOOL_OP = OR
    TEST_CLAUSE = TEST @Value(MessageType) = ERROR
    TEST_MODE = TEST
    PASSED -> Terminator_2
Terminator_2 [off]
    MESSAGE = Translation Terminated: @Value(MessageString)

FME custom transformer DatabricksAPICaller
Custom Transformer to call Databricks API

Parameters:
- COMMAND =
- DOMAIN =
- JOBID =
- METHOD =
- PARAMETER =
- RUNID =
- TOKEN =

DatabrickAPICallerInput (input)
    -> ParameterFetcher
ParameterFetcher
    ATTR_LIST = _TOKEN $(TOKEN) _DOMAIN $(DOMAIN)
    -> CallDatabricksJob
Note: Call databricks API
CallDatabricksJob: PythonCaller
    NEW_ATTRIBUTES = RunId status result num_records has_overlaps error noError cmd fields
    PYTHONSOURCE:
      import fme
      import fmeobjects
      import json
      import base64
      import requests
      import re


      # Template Function interface:
      # When using this function, make sure its name is set as the value of
      # the 'Class or Function to Process Features' transformer parameter
      def dbfs_rpc(action, body,TOKEN,BASE_URL):
        """ A helper function to make the API request, request/response is encoded/decoded as JSON """
        response = requests.post(
          BASE_URL + action,
          headers={"Authorization":"Bearer " +str(TOKEN) },
          json=body
        )
        return response.json()

      def dbfs_get_rpc(action, body,TOKEN,BASE_URL):
        """ A helper function to make the API request, request/response is encoded/decoded as JSON """
        response = requests.get(
          BASE_URL + action,
          headers={"Authorization":"Bearer " + str(TOKEN) },
          params= body
        )
        return response.json()



      def processFeature(feature):
          pass

      # Template Class Interface:
      # When using this class, make sure its name is set as the value of
      # the 'Class or Function to Process Features' transformer parameter
      class FeatureProcessor(object):
          def __init__(self):
              pass
          def input(self,feature):
              runId= 0
              status=""
              result=""
              num_records =0
              has_overlaps =0
              error= ""
              noError=0
              cmd =0
              fields=""
              try:

                  raw_data = {}
                  if feature.getAttribute('RunId'):
                      raw_data['run_id']= str(feature.getAttribute('RunId'))
                  if feature.getAttribute('JobId'):
                      raw_data['job_id']= feature.getAttribute('JobId')

                  if feature.getAttribute('Parameter'):
                      paramTxt = "{" + str(feature.getAttribute('Parameter')) + "}"
                      formatedParam = paramTxt.replace("\n"," ").replace("\t", " ").replace("  "," ")
                      parameter = json.loads(formatedParam)
                      raw_data['notebook_params'] = parameter

                  DOMAIN = str(feature.getAttribute('_DOMAIN'))
                  TOKEN = str(feature.getAttribute('_TOKEN'))
                  BASE_URL = 'https://%s/api/2.0/jobs/' % (DOMAIN)


                  if feature.getAttribute('Method') == 'POST':
                      handle = dbfs_rpc(feature.getAttribute('Command'), raw_data,TOKEN, BASE_URL)
                  else:
                      handle = dbfs_get_rpc(feature.getAttribute('Command'), raw_data,TOKEN, BASE_URL)
                  noError=0

                  if ('run_id' in handle):
                      runId= handle['run_id']
                  else:
                      runId= str(feature.getAttribute('RunId'))

                  if 'metadata' in handle:
                      if 'state' in handle['metadata']:
                          if 'life_cycle_state' in handle['metadata']['state']:
                              status = handle['metadata']['state']['life_cycle_state']
                          if 'result_state' in handle['metadata']['state']:
                              result = handle['metadata']['state']['result_state']

                      if status == 'TERMINATED' : # and 'notebook_output' in handle:
                          if 'result' in  handle['notebook_output']:
                              output = handle['notebook_output']['result'].replace('\n', ' ').replace('\r', '').replace('\t', '').replace("  ","")
                              res = json.loads(output)
                              noError = res['status']
                              cmd = res['cmd']
                              error = res['error']
                              if 'num_records' in res:
                                  num_records = res['num_records']
                              if 'has_overlaps' in res:
                                  has_overlaps = res['has_overlaps']
                              if 'fields' in res:
                                  fields = str(res['fields'])
                                  fields = fields.replace("'fieldname': '", '"fieldname": "')
                                  fields = fields.replace("', 'grouporder':",'", "grouporder":')
                                  fields = fields.replace("'fieldValue': '",'"fieldValue": "')
                                  fields = fields.replace("', 'TotalRecord':",'", "TotalRecord":')
                                  fields = fields.replace("'fieldValue'",'"fieldValue"')
                                  fields = fields.replace("'TotalRecord'",'"TotalRecord"')

              except Exception as err:
                  print("DATABRICKS ERRROR")
                  print("error:" + str(err))
                  feature.setAttribute("RunId",0)
                  feature.setAttribute("error",str(err))
                  feature.setAttribute("noError",0)

              feature.setAttribute("RunId",runId)
              feature.setAttribute("status",status)
              feature.setAttribute("result",result)
              feature.setAttribute("num_records",num_records)
              feature.setAttribute("has_overlaps",has_overlaps)
              feature.setAttribute("error",error)
              feature.setAttribute("noError",noError)
              feature.setAttribute("cmd",cmd)
              feature.setAttribute("fields",fields)
              self.pyoutput(feature)

          def close(self):
              pass
    PYTHONSYMBOL = FeatureProcessor
    -> CallDatabricksJob_Output (output)
CallDatabricksJob_Output (output)

FME custom transformer CreateFieldParts

Parameters:
- FIELDID =

Input (input)
    -> SQLExecutor [INITIATOR]
SQLExecutor
    ATTR_IGNORE_NULLS = No
    COMBINE_ATTRS = Keep Initiator Attributes if Conflict
    COMBINE_GEOM = Initiator Geometry Only
    DATASET = CubeManager
    EXPOSED_ATTRIBUTE_LIST = Filename ExcludedValues
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = CubeManager
    MSSQL_ADO_QUERY_FEATURE_TYPES_FOR_MERGE_FILTERS = Yes
    SQL_STATEMENT:
      select Filename,concat(ExcludedValues,',',
          (select ExcludeValues
           from Fields
           where FieldId = @Value(FieldId)
          )) ExcludedValues
      from fieldparts
      where Fieldid =@Value(FieldId)
    RESULT -> PyRemoveLastComma
Note: If fields have no ExcludeddValues data, remove last comma
PyRemoveLastComma: PythonCaller
    PYTHONSOURCE:
      import fme
      import fmeobjects
      # Template Function interface:
      # When using this function, make sure its name is set as the value of
      # the 'Class or Function to Process Features' transformer parameter
      def processFeature(feature):
          pass

      # Template Class Interface:
      # When using this class, make sure its name is set as the value of
      # the 'Class or Function to Process Features' transformer parameter
      class FeatureProcessor(object):
          def __init__(self):
              pass
          def input(self,feature):
              excl = feature.getAttribute('ExcludedValues')
              excl= excl.strip()
              if (excl.endswith(',')):
                  excl=   excl.rstrip(excl[-1])

              feature.setAttribute('ExcludedValues', excl)
              self.pyoutput(feature)
          def close(self):
              pass
    PYTHONSYMBOL = FeatureProcessor
    -> AttributeCreator
AttributeCreator
    ATTR_TABLE = SET_TO FieldParts = {"FileName":"@ReplaceString(@Value(Filename),".tif","")", "NoData": [@Value(ExcludedValues)]}
    -> Aggregator
Aggregator
    ACCUM_ATTRS_NAME = Use Attributes From One Feature
    AGGREGATE_TYPE = Homogeneous Collection (If Possible)
    CONCAT_ATTRS = FieldParts
    GROUP_BY = FieldId
    MODE = Geometry - Assemble One Level
    SEP = ,
    AGGREGATE -> Output (output)
Output (output)

FME custom transformer UploadFilesToHDFS

Parameters:
- OUTPUTFILENAME =
- _DATASET =

UploadFilesToDBFS (input)
    -> AttributeCreator
AttributeCreator
    ATTR_TABLE = SET_TO destFile = CubeSourceDataFile/@Value(OutputFilename)
    -> AzureBlobUploader
Note: Send SourceFile to Microsoft Azure
AzureBlobUploader
    ACCOUNT = cwsblobstorage01
    BLOB_NAME = @Value(destFile)
    CONTAINER = cwsblob01
    KEY =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
    SRC_DATA = @Value(_dataset)
    SRC_TYPE = FilePath
    Success -> Output (output)
    Fail -> Error (output)
    Fail -> Inspector
Output (output)
Error (output)
Inspector [off]

FME custom transformer WaitUntilDatabtricksJobCompleted

Parameters:
- MINUTESTOTIMEOUT =
- RUNID =
- STARTTIME =

CheckJobStatus_Input (input)
    -> CheckRunStatus [DatabrickAPICallerInput]
CheckRunStatus: DatabricksAPICaller
    COMMAND = runs/get-output
    DOMAIN = northeurope.azuredatabricks.net
    METHOD = GET
    RUNID = @Value(RunId)
    TOKEN =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
    CallDatabricksJob_Output -> CurrentTimer
CurrentTimer: AttributeCreator
    ATTR_TABLE = SET_TO CurrentTime = @DateTimeNow()
    -> TestJobStatus
TestJobStatus: TestFilter
    DEFAULT_VALUE = <UNFILTERED>
    TEST_LIST = "BOOL_OP,OR,COMPOSITE_TEST,""""""1"""""",TEST_CLAUSE,TEST @Value(status) = TERMINATED",TERMINATED,"BOOL_OP,OR,COMPOSITE_TEST,""""""1"""""",TEST_CLAUSE,TEST @Value(status) = PENDING",PENDING,"BOOL_OP,OR,COMPOSITE_TEST,""""""1"""""",TEST_CLAUSE,TEST @Value(status) = RUNNING",RUNNING,"BOOL_OP,OR,COMPOSITE_TEST,""""""1"""""",TEST_CLAUSE,TEST @Value(status) = TERMINATING",TERMINATING
    TERMINATED -> TestFilter_TERMINATED (output)
    PENDING -> TimeOutStartingCluster
    RUNNING -> Decelerator
    TERMINATING -> Decelerator
    <UNFILTERED> -> Decelerator
TimeOutStartingCluster: Tester
    BOOL_OP = OR
    COMPOSITE_TEST = 1
    TEST_CLAUSE = TEST @Value(CurrentTime) >= @DateTimeAdd(@Value(StartTime), @DateTimeIntervalCreate(0,0,0,0,@Value(MinutesToTimeout),0) )
    TEST_MODE = TEST
    PASSED -> CancelRun [DatabrickAPICallerInput]
    FAILED -> Decelerator
CancelRun: DatabricksAPICaller
    COMMAND = runs/cancel
    DOMAIN = northeurope.azuredatabricks.net
    METHOD = POST
    RUNID = @Value(RunId)
    TOKEN =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
    CallDatabricksJob_Output -> SetErrorInDatabricksResult
SetErrorInDatabricksResult: AttributeCreator
    ATTR_TABLE:
      SET_TO error = Timeout starting cluster
      SET_TO noError = 0
      SET_TO num_records = 0
      SET_TO has_overlaps = 0
      SET_TO cmd = 0
    -> TestFilter_TERMINATED (output)
TestFilter_TERMINATED (output)
Decelerator
    DECEL_TYPE = Per Feature Delay
    DELAY = 15
    -> CheckJobStatus_Input (output)
CheckJobStatus_Input (output)

FME custom transformer DeleteDimensionStats

Parameters:
- FILEID =
- SQLDWTABLENAME =
- fields =

Iterator (input)
    -> Counter
Initiator (input)
    -> Counter
    -> DatabaseDeleter
Counter
    CNT_ATTR = _count
    DOMAIN = counter
    SCOPE = Global
    START = 1
    -> SQLExecutor [INITIATOR]
SQLExecutor
    COMBINE_ATTRS = Result Attributes Only
    COMBINE_GEOM = Initiator Geometry Only
    DATASET = CubeManager
    EXPOSED_ATTRIBUTE_LIST = FileId NumFields SQLDWTableName
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = CubeManager
    MSSQL_ADO_QUERY_FEATURE_TYPES_FOR_MERGE_FILTERS = Yes
    SQL_STATEMENT:
      select FieldStatistics.fileid, count(FieldStatisticsId) as NumFields , Files.SQLDWTableName
      from [dbo].[FieldStatistics] inner join files on
      	files.fileid = FieldStatistics.fileid

      where FieldStatistics.fileid = @Value(FileId)
      Group BY
      	FieldStatistics.fileid,Files.SQLDWTableName
    RESULT -> ParameterFetcher_2
    INITIATOR -> Tester
ParameterFetcher_2
    ATTR_LIST = fields $(fields)
    -> TestFilter
TestFilter
    DEFAULT_VALUE = NoFields
    TEST_LIST = "BOOL_OP,OR,COMPOSITE_TEST,""""""1"""""",TEST_CLAUSE,TEST @Value(NumFields) > 0",Fields
    Fields -> Decelerator
    NoFields -> Output (output)
Decelerator
    DECEL_TYPE = Per Feature Delay
    DELAY = 15
    -> Iterator (output)
Iterator (output)
Tester
    BOOL_OP = AND
    COMPOSITE_TEST = 1 AND 2
    TEST_CLAUSE:
      TEST @Value(_count) = 1
      TEST @Value(_matched_records) = 0
    TEST_MODE = TEST
    PASSED -> Output (output)
Output (output)
DatabaseDeleter
    CONDITION = WHERE Clause
    DATASET = CubeManager
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = CubeManager
    MSSQL_ADO_QUERY_FEATURE_TYPES_FOR_MERGE_FILTERS = Yes
    TABLE = dbo.FieldStatistics
    WHERE_CLAUSE = FileId = @Value(FileId)
