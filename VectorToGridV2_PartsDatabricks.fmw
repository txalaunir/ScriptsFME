FME workspace VectorToGridV2_PartsDatabricks.fmw
Title: Vector2GridV2_Parts
Description: This workspace will take any ESRI Shapefile as input and produce gridded csv files.
The workspace will first analyze the bounds of the source data and submit subjobs in order to process the data in tiles.
The columns in the resulting csv should be x y GRIDNUM + exact spelling of fields in in source shapefile.
Parameters:
    GRIDSIZE Size in source coordinate system units 
    OUTPUT_FOLDER "C:\Temp\vectortogrid" 
    PASSWORD "********" 
    Parameters that will be used when submitted as a subprocess: 
    SUBPROCESS "NO" 
    MINX "" 
    MINY "" 
    MAXX "" 
    MAXY "" 
    OUTPUT_FEATURETYPE_BASENAME ""

Parameters:
- FME_JOB_ID = 0
- FME_USER_PARAM_PRIVATE_GRP =
- FileId =
- File_Type =
- GRIDSIZE =
- MAXX =
- MAXY =
- MINX =
- MINY =
- OUTPUT_FEATURETYPE_BASENAME =
- OUTPUT_FOLDER =
- PC_MAPPING =
- SOURCE_SHAPE_DATASET =

Creator
    COORDS = $(MINX) $(MINY) $(MAXX) $(MAXY)
    COORDSYS = EPSG:3035
    GEOMTYPE = 2D Min/Max Box
    NUM = 1
    CREATED -> AttributeCreator_2
TestFilter
    DEFAULT_VALUE = <UNFILTERED>
    TEST_LIST = "BOOL_OP,OR,COMPOSITE_TEST,""""""1"""""",TEST_CLAUSE,TEST $(File_Type) = shp",shp,"BOOL_OP,OR,COMPOSITE_TEST,""""""1"""""",TEST_CLAUSE,TEST $(File_Type) = gdb",gdb,"BOOL_OP,OR,COMPOSITE_TEST,""""""1"""""",TEST_CLAUSE,TEST $(File_Type) = gpkg",gpkg
    shp -> FeatureReaderSHP [INITIATOR]
    gdb -> FeatureReaderGDB [INITIATOR]
    gpkg -> FeatureReaderGPKG [INITIATOR]
FeatureReaderSHP
    ATTR_ACCUM_MODE = Only Use Result
    COMBINE_GEOM = Use Result
    DATASET = $(SOURCE_SHAPE_DATASET)
    ESRISHAPE_CHECK_NUMERIC_FIELDS = yes
    ESRISHAPE_DISSOLVE_HOLES = no
    ESRISHAPE_ENCODING = utf-8
    ESRISHAPE_MEASURES_AS_Z = no
    ESRISHAPE_NUMERIC_TYPE_ATTRIBUTE_HANDLING = STANDARD_TYPES
    ESRISHAPE_REPORT_BAD_GEOMETRY = no
    ESRISHAPE_SIMPLE_DONUT_GEOMETRY = simple
    ESRISHAPE_TRIM_PRECEDING_SPACES = yes
    ESRISHAPE_UPPER_CASE_ATTR_NAMES = No
    ESRISHAPE_USE_SEARCH_ENVELOPE = NO
    FORMAT = ESRISHAPE
    INTERACT = Envelope Intersects
    OUTPUT_FEATURES_DISPLAY = Schema and Data Features
    <OTHER> -> FeatureMerger [REQUESTOR]
    INITIATOR -> FeatureMerger [SUPPLIER]
FeatureReaderGDB
    ATTR_ACCUM_MODE = Only Use Result
    COMBINE_GEOM = Use Result
    DATASET = $(SOURCE_SHAPE_DATASET)
    FORMAT = GEODATABASE_FILE
    GEODATABASE_FILE_ALIAS_MODE = NONE
    GEODATABASE_FILE_CACHE_MULTIPATCH_TEXTURES = yes
    GEODATABASE_FILE_CHECK_SIMPLE_GEOM = no
    GEODATABASE_FILE_CREATE_FEATURE_TABLES_FROM_DATA = Yes
    GEODATABASE_FILE_FEATURE_READ_MODE = Features
    GEODATABASE_FILE_IGNORE_NETWORK_INFO = yes
    GEODATABASE_FILE_IGNORE_RELATIONSHIP_INFO = yes
    GEODATABASE_FILE_MERGE_FEAT_LINKED_ANNOS = no
    GEODATABASE_FILE_QUERY_FEATURE_TYPES_FOR_MERGE_FILTERS = Yes
    GEODATABASE_FILE_RESOLVE_DOMAINS = no
    GEODATABASE_FILE_RESOLVE_SUBTYPE_NAMES = yes
    GEODATABASE_FILE_SPLIT_COMPLEX_ANNOS = no
    GEODATABASE_FILE_SPLIT_COMPLEX_EDGES = no
    GEODATABASE_FILE_SPLIT_MULTI_PART_ANNOS = no
    GEODATABASE_FILE_STRIP_GUID_GLOBALID_BRACES = no
    GEODATABASE_FILE_TRANSLATE_SPATIAL_DATA_ONLY = no
    GEODATABASE_FILE_USE_SEARCH_ENVELOPE = NO
    INTERACT = Envelope Intersects
    OUTPUT_FEATURES_DISPLAY = Schema and Data Features
    <OTHER> -> FeatureMerger [REQUESTOR]
    INITIATOR -> FeatureMerger [SUPPLIER]
FeatureReaderGPKG
    ATTR_ACCUM_MODE = Only Use Result
    COMBINE_GEOM = Use Result
    DATASET = $(SOURCE_SHAPE_DATASET)
    FORMAT = OGCGEOPACKAGE
    INTERACT = Envelope Intersects
    OGCGEOPACKAGE_ENCODE_FEATURE_TYPE_AND_ATTR_NAMES = YES
    OGCGEOPACKAGE_ENFORCE_FOREIGN_KEY_INTEGRITY = YES
    OGCGEOPACKAGE_OPEN_SINGLE_RASTER_AS_SUBDATASET = YES
    OGCGEOPACKAGE_QUERY_FEATURE_TYPES_FOR_MERGE_FILTERS = Yes
    OGCGEOPACKAGE_READ_BOOLEANS_AS_YES_NO = YES
    OGCGEOPACKAGE_READ_NULLS = YES
    OGCGEOPACKAGE_USE_SEARCH_ENVELOPE = NO
    OUTPUT_FEATURES_DISPLAY = Schema and Data Features
    <OTHER> -> FeatureMerger [REQUESTOR]
    INITIATOR -> FeatureMerger [SUPPLIER]
FeatureMerger
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> FeatureCounter
FeatureCounter: Counter
    CNT_ATTR = featureCount
    DOMAIN = FeatureCounter
    SCOPE = Global
    START = 0
    -> LOgger
LOgger: PythonCaller
    PYTHONSOURCE:
      import fme
      import fmeobjects
      # Template Function interface:
      # When using this function, make sure its name is set as the value of
      # the 'Class or Function to Process Features' transformer parameter
      def processFeature(feature):
          pass

      # Template Class Interface:
      # When using this class, make sure its name is set as the value of
      # the 'Class or Function to Process Features' transformer parameter
      class FeatureProcessor(object):
          def __init__(self):
              pass
          def input(self,feature):
              num =str( feature.getAttribute('_matched_records'))
              count = feature.getAttribute('featureCount')
              if (count % 20 ==0):
                  print("######")
                  print(str(count) + "/" + num)
                  print("######")
              self.pyoutput(feature)
          def close(self):
              pass
    PYTHONSYMBOL = FeatureProcessor
    -> LessThan20kFeatures
LessThan20kFeatures: Tester
    BOOL_OP = OR
    COMPOSITE_TEST = 1
    TEST_CLAUSE = TEST @Value(_matched_records) < 20000
    TEST_MODE = TEST
    PASSED -> GeometryFilter
    FAILED -> FilteringGridAccumulator
GeometryFilter
    BREAK_AGG = No
    GEOM_PORT_NAMES = Point Line Area
    POINT -> Counter_2
    LINE -> VertexExtractor
    LINE -> Bufferer
    AREA -> Counter
VertexExtractor
    Point -> Bufferer
    Point -> Counter_2
Counter_2
    CNT_ATTR = _feature_id
    DOMAIN = counter
    SCOPE = Global
    START = 0
    -> PointCloudCombiner_4
PointCloudCombiner_4
    ACCUM_ATTRS_NAME = Yes
    EXTRACT_RASTER_NODATA_NAME = No
    GROUP_BY = _feature_id
    SPACING = 1.0
    -> PointCloudComponentRemover
Bufferer
    ANGLE = 22.5
    CAP_STYLE = Arc
    CORNER_STYLE = Arc
    MODE = AREA
    OFFSET = 0.01
    OFFSET_UNITS = NONE
    PRECISION = APPROX
    BUFFERED -> Counter
Counter
    CNT_ATTR = _feature_id
    DOMAIN = counter
    SCOPE = Global
    START = 0
    -> PythonCaller
    -> Clipper [CLIPPER]
PythonCaller
    PYTHONSOURCE:
      import fme
      import fmeobjects
      # Template Function interface:
      # When using this function, make sure its name is set as the value of
      # the 'Class or Function to Process Features' transformer parameter
      def processFeature(feature):
          pass

      # Template Class Interface:
      # When using this class, make sure its name is set as the value of
      # the 'Class or Function to Process Features' transformer parameter
      class FeatureProcessor(object):
          def __init__(self):
              pass
          def input(self,feature):
              featId = feature.getAttribute('_feature_id')
              totalFeats = feature.getAttribute('_matched_records')
              if (int(featId) % 1000 == 0) :
                  print("***")
                  print(str(featId) + " / " + str(totalFeats))

              self.pyoutput(feature)
          def close(self):
              pass
    PYTHONSYMBOL = FeatureProcessor
    -> 3DForcer_2
3DForcer_2
    KEEPZVAL = No
    ZVALATTR = 1
    -> NumericRasterizer_2
NumericRasterizer_2
    ANTI_ALIASING = No
    BACKGROUND_VALUE = 0
    FILL_WITH_NODATA = Yes
    GROUND_EXTENTS_MAX_X = $(MAXX)
    GROUND_EXTENTS_MAX_Y = $(MAXY)
    GROUND_EXTENTS_MIN_X = $(MINX)
    GROUND_EXTENTS_MIN_Y = $(MINY)
    GROUP_BY = _feature_id
    INTERPRETATION_TYPE = UInt8
    ROWCOL_OR_CELLSIZE = CellSize
    SPECIFY_GROUND_EXTENTS = Specify ground extents
    TOLERANCE = 0.5
    X_CELL_SIZE = $(GRIDSIZE)
    Y_CELL_SIZE = $(GRIDSIZE)
    RASTER -> PointCloudCombiner_2
PointCloudCombiner_2
    ACCUM_ATTRS_NAME = Yes
    EXTRACT_RASTER_NODATA_NAME = No
    GROUP_BY = _feature_id
    SPACING = 1.0
    -> PointCloudPropertyExtractor
PointCloudPropertyExtractor
    CALCULATE_EXTENTS_DISPLAY = Yes
    POINT_COMPONENTS = "x    y    z   "
    -> Clipper [CLIPPEE]
Clipper
    ATTR_ACCUM_MODE = Merge Clipper
    ATTR_CONFLICT_RES = Use Clippee
    BOUNDARY_CASES = Treat as Inside
    CLEANING_TOLERANCE = None
    CLIPPED_ATTR = _clipped
    CLIP_TYPE = Single Clipper
    CONNECT_Z_MODE = First Wins
    CREATE_AGGREGATES = Yes
    GROUP_BY = _feature_id
    LINES_AS_SEGMENTS = No
    MEASURE_TYPE = Continuous
    MISSING_VAL_MODE = Compute
    PRESERVE_CLIPPEE_EXTENTS = No
    VAL_SOURCE = Clipper and Clippee
    INSIDE -> Tester_2
Tester_2
    BOOL_OP = OR
    COMPOSITE_TEST = 1
    TEST_CLAUSE = NUM_TEST @Value(_num_points) > 0
    TEST_MODE = NUM_TEST
    PASSED -> PointCloudComponentRemover
PointCloudComponentRemover
    COMPONENTS_TO_REMOVE = z
    -> PointCloudExpressionEvaluator_3
PointCloudExpressionEvaluator_3
    EXPRESSION_TABLE = x Int64 @floor(@Component(x)/$(GRIDSIZE)) * $(GRIDSIZE) y Int64 @floor(@Component(y)/$(GRIDSIZE)) * $(GRIDSIZE)
    RESULT -> PointCloudEeaGridNumComponentAdder
PointCloudEeaGridNumComponentAdder
    PC_COMPONENT = gid
    TARGET_GRID = $(GRIDSIZE)
    Result -> TestFilter_3
TestFilter_3
    DEFAULT_VALUE = <UNFILTERED>
    TEST_LIST = "BOOL_OP,OR,COMPOSITE_TEST,""""""1"""""",TEST_CLAUSE,TEST $(File_Type) = shp",shp,"BOOL_OP,OR,COMPOSITE_TEST,""""""1"""""",TEST_CLAUSE,TEST $(File_Type) = gdb",gdb,"BOOL_OP,OR,COMPOSITE_TEST,""""""1"""""",TEST_CLAUSE,TEST $(File_Type) = gpkg",gpkg
    shp -> FeatureReader_SchemaSHP [INITIATOR]
    gpkg -> FeatureReader_SCHEMA_GPKG [INITIATOR]
FeatureReader_SchemaSHP
    ATTR_ACCUM_MODE = Only Use Result
    COMBINE_GEOM = Use Result
    DATASET = $(SOURCE_SHAPE_DATASET)
    ESRISHAPE_CHECK_NUMERIC_FIELDS = yes
    ESRISHAPE_DISSOLVE_HOLES = no
    ESRISHAPE_ENCODING = utf-8
    ESRISHAPE_MEASURES_AS_Z = no
    ESRISHAPE_NUMERIC_TYPE_ATTRIBUTE_HANDLING = STANDARD_TYPES
    ESRISHAPE_REPORT_BAD_GEOMETRY = no
    ESRISHAPE_SIMPLE_DONUT_GEOMETRY = simple
    ESRISHAPE_TRIM_PRECEDING_SPACES = yes
    ESRISHAPE_UPPER_CASE_ATTR_NAMES = No
    ESRISHAPE_USE_SEARCH_ENVELOPE = NO
    FORMAT = ESRISHAPE
    INTERACT = <No Spatial Filter>
    OUTPUT_FEATURES_DISPLAY = Schema Features
    <SCHEMA> -> PythonCaller_2
    INITIATOR -> PythonCaller_2
FeatureReader_SCHEMA_GPKG
    ATTR_ACCUM_MODE = Only Use Result
    COMBINE_GEOM = Use Result
    DATASET = $(SOURCE_SHAPE_DATASET)
    FORMAT = OGCGEOPACKAGE
    INTERACT = <No Spatial Filter>
    OGCGEOPACKAGE_ENCODE_FEATURE_TYPE_AND_ATTR_NAMES = YES
    OGCGEOPACKAGE_ENFORCE_FOREIGN_KEY_INTEGRITY = YES
    OGCGEOPACKAGE_OPEN_SINGLE_RASTER_AS_SUBDATASET = YES
    OGCGEOPACKAGE_QUERY_FEATURE_TYPES_FOR_MERGE_FILTERS = Yes
    OGCGEOPACKAGE_READ_BOOLEANS_AS_YES_NO = YES
    OGCGEOPACKAGE_READ_NULLS = YES
    OGCGEOPACKAGE_USE_SEARCH_ENVELOPE = NO
    OUTPUT_FEATURES_DISPLAY = Schema Features
    <SCHEMA> -> PythonCaller_2
    INITIATOR -> PythonCaller_2
Note: Updates: / Changed so that all fields are added as string with empty value for null / Using wwjd-encoding when supplying component values so that non-ascii chracters can be handled as well
PythonCaller_2
    NEW_ATTRIBUTES = _components_added _pc_mapping
    PYTHONSOURCE:
      import fmeobjects
      from itertools import chain

      class FeatureProcessor(object):
          def __init__(self):
              self.schema =  None
              self.session = fmeobjects.FMESession()

          def input(self,feature):
              # We totally rely on schema feature entering first
              if self.schema is None:
                  self.schema = {name: 'STRING' for name in feature.getAttribute('attribute{}.name')}
                  return

              components = []
              for name, component_type in self.schema.items():
                  is_null, is_missing, fmeobjects_type = feature.getAttributeNullMissingAndType(name)
                  func_args = []
                  if name == "x" or name == "y":
                      name = "_" + name
                  if is_null or is_missing:
                      func_args = [name,component_type,'']
                  else:
                      val = self.session.encodeToFMEParsableText(str(feature.getAttribute(name))).replace('\x00','')
                      func_args = [name,component_type,val]
                  funcspec = '@AddPointCloudComponents(' +  ",".join(func_args) + ')'
                  feature.performFunction(funcspec)
                  components.append(name)

              components.append('GridNum10Km')
              components.append('AreaHa')

              feature.setAttribute('_components_added', ','.join(components))
              components = ['x','y'] + components
              pc_mapping = list(chain.from_iterable(zip(components,components)))
              feature.setAttribute('_pc_mapping', ','.join(pc_mapping))
              self.pyoutput(feature)
          def close(self):
              del self.session
    PYTHONSYMBOL = FeatureProcessor
    -> PointCloudCombiner_3
PointCloudCombiner_3
    ACCUM_ATTRS_NAME = No
    EXTRACT_RASTER_NODATA_NAME = No
    GROUP_BY = _pc_mapping _components_added
    SPACING = 1.0
    -> PointCloudExpressionEvaluator_2
PointCloudExpressionEvaluator_2
    EXPRESSION_TABLE:
      GridNum10Km Int64 @int64(@int64(@Component(gid)) & @int64(-4294967296))
       AreaHa Real64 pow($(GRIDSIZE)/100,2)
    RESULT -> AttributeCreator
AttributeCreator
    ATTR_TABLE:
      SET_TO _filename = $(OUTPUT_FEATURETYPE_BASENAME)_$(FME_JOB_ID)
      SET_TO _field_names_filecontent = x,y,GridNum,@Value(_components_added)
      SET_TO _filed_names_filename = @Value(_filename).fieldnames
    -> FeatureWriter [Output]
FeatureWriter
    DATASET = $(OUTPUT_FOLDER)
    DATASET_ATTR = _dataset
    FEATURE_TYPE_LIST_ATTR = _feature_type
    FORMAT = POINTCLOUDXYZ
    MORE_SUMMARY_ATTRS = _filename
    POINTCLOUDXYZ_APPEND = No
    POINTCLOUDXYZ_COORDINATE_SYSTEM_GRANULARITY = FEATURE
    POINTCLOUDXYZ_DESTINATION_DATASETTYPE_VALIDATION = Yes
    POINTCLOUDXYZ_ENCODING = UTF-8
    POINTCLOUDXYZ_EXTENSION = .csv.gz
    POINTCLOUDXYZ_INCLUDE_FIELD_NAME = no
    POINTCLOUDXYZ_QUOTE_FIELD_NAMES = if_needed
    POINTCLOUDXYZ_QUOTE_OUTPUT = if_needed
    POINTCLOUDXYZ_SEPARATOR = |
    POINTCLOUDXYZ_WRITE_UTF8_BOM = yes
    TOTAL_FEATURES_WRITTEN_ATTR = _total_features_written
UpdateGridSize: AttributeCreator
    ATTR_TABLE = SET_TO GridWidth = @Evaluate(@Value(GridWidth)/5)
    -> FilteringGridAccumulator
FilteringGridAccumulator
    GRIDWIDTH = @Value(GridWidth)
    RENDER_SIZE = "@int16(@Value(GridWidth)) "
    GridCells -> Tester
Tester
    BOOL_OP = AND
    COMPOSITE_TEST = 1 AND 2 AND 3 AND 4
    TEST_CLAUSE:
      TEST @Value(_xmax) <= $(MAXX)
      TEST @Value(_ymax) <= $(MAXY)
      TEST @Value(_xmin) >= $(MINX)
      TEST @Value(_ymin) >= $(MINY)
    TEST_MODE = TEST
    PASSED -> FMEServerJobSubmitter_2
Note: Execute VectorToGridV2_Parts.fmw
FMEServerJobSubmitter_2
    BLOCKING = Yes
    PRIORITY = 150
    PROCESSING_MODE = In Parallel
    REPOSITORY = CubeSubProcessess
    SERVER_CONNECTION = diaz FME Server
    WORKSPACE_NAME = VectorToGridV2_PartsDatabricks.fmw
    WORKSPACE_PARAMETERS = SOURCE_SHAPE_DATASET list $(SOURCE_SHAPE_DATASET) GRIDSIZE string $(GRIDSIZE) MINX string @Value(_xmin) MINY string @Value(_ymin) MAXX string @Value(_xmax) MAXY string @Value(_ymax) OUTPUT_FOLDER string $(OUTPUT_FOLDER) OUTPUT_FEATURETYPE_BASENAME string $(OUTPUT_FEATURETYPE_BASENAME) FileId string $(FileId) File_Type string $(File_Type)

Bookmark: Build smaller grid for high resolution dimensiosn
AttributeCreator_2
    ATTR_TABLE = SET_TO GridWidth = @Evaluate($(MAXX)-$(MINX))
    -> TestFilter_2
TestFilter_2
    DEFAULT_VALUE = HIGH_RES
    TEST_LIST = "BOOL_OP,OR,COMPOSITE_TEST,""""""1"""""",TEST_CLAUSE,TEST $(GRIDSIZE) > 10",LOW_RES,"BOOL_OP,OR,COMPOSITE_TEST,""""""1"""""",TEST_CLAUSE,TEST @Value(GridWidth) <= 20000",LOW_RES_10m
    LOW_RES -> TestFilter
    LOW_RES_10m -> TestFilter
    HIGH_RES -> UpdateGridSize [off]
    HIGH_RES -> TestFilter

FME custom transformer PointCloudEeaGridNumComponentAdder

Parameters:
- PC_COMPONENT =
- TARGET_GRID =

Input (input)
    -> GeometryFilter
GeometryFilter
    BREAK_AGG = No
    GEOM_PORT_NAMES = "Point Cloud"
    POINTCLOUD -> TestFilter
    <UNFILTERED> -> Rejected (output)
TestFilter
    DEFAULT_VALUE = <UNFILTERED>
    TEST_LIST = BOOL_OP,OR,COMPOSITE_TEST,<Unused>,TEST_CLAUSE,"TEST $(TARGET_GRID) = 250",250
    250 -> PointCloudExpressionEvaluator_2
    <UNFILTERED> -> AttributeCreator
PointCloudExpressionEvaluator_2
    EXPRESSION_TABLE:
      $(PC_COMPONENT) Int64 1099511627776
      	+ (@int64(@floor(@Component(x) / 1000000)))      * 68719476736
      	+ (@int64(@floor(@Component(y) / 1000000)))      *  4294967296
      	+ (@int64(@floor(@Component(x) /  100000)) % 10) *   268435456
      	+ (@int64(@floor(@Component(y) /  100000)) % 10) *    16777216
      	+ (@int64(@floor(@Component(x) /   10000)) % 10) *     1048576
      	+ (@int64(@floor(@Component(y) /   10000)) % 10) *       65536
      	+ (@int64(@floor(@Component(x) /    1000)) % 10) *        4096
      	+ (@int64(@floor(@Component(y) /    1000)) % 10) *         256
      	+ (@int64(@floor(@Component(x) /     250))  & 3) *          16
      	+ (@int64(@floor(@Component(y) /     250))  & 3)
    RESULT -> AttributeRemover
AttributeCreator
    ATTR_TABLE = SET_TO _pointcloud_2_eeagrid_target_grid = $(TARGET_GRID)
    -> AttributeValueMapper
AttributeValueMapper
    DIRECTION = Forward (Source To Destination)
    LUT = 100,1099511627775,1000,1099511627520,10000,1099511562240,100000,1099494850560,1000000,1095216660480
    SRC = _pointcloud_2_eeagrid_target_grid
    VAL_ATTR = _pointcloud_2_eeagrid_target_grid_mask
    -> PointCloudExpressionEvaluator
PointCloudExpressionEvaluator
    EXPRESSION_TABLE:
      $(PC_COMPONENT) Int64  @int64((@int64(@floor(@Component(x) / 1000000)))      * pow(16,13)
      	+ (@int64(@floor(@Component(y) / 1000000)))      *  pow(16,12)
      	+ (@int64(@floor(@Component(x) /  100000)) % 10) *   pow(16,11)
      	+ (@int64(@floor(@Component(y) /  100000)) % 10) *   pow(16,10 )
      	+ (@int64(@floor(@Component(x) /   10000)) % 10) *     pow(16,9)
      	+ (@int64(@floor(@Component(y) /   10000)) % 10) *       pow(16,8)
      	+ (@int64(@floor(@Component(x) /    1000)) % 10) *        pow(16,7)
      	+ (@int64(@floor(@Component(y) /    1000)) % 10) *        pow(16,6)
      	+ (@int64(@floor(@Component(x) /     100)) % 10) *         pow(16,5)
      	+ (@int64(@floor(@Component(y) /     100)) % 10)  *        pow(16,4)
      	+ (@int64(@floor(@Component(x) /     10)) % 10)    *        pow(16,3)
      	+ (@int64(@floor(@Component(y) /     10)) % 10)  *        pow(16,2)
      	+ (@int64(@floor(@Component(x)           ))  %10  )  *        pow(16,1)
       	+ (@int64(@floor(@Component(y)           ))   %10 )
      )
    RESULT -> AttributeRemover
AttributeRemover
    REMOVE_ATTRS = _pointcloud_2_eeagrid_target_grid_mask,_pointcloud_2_eeagrid_target_grid
    -> Result (output)
Result (output)
Rejected (output)

FME custom transformer FilteringGridAccumulator

Parameters:
- GRIDWIDTH =
- RENDER_SIZE =

Input (input)
    -> VariableSetter
VariableSetter
    SCOPE = Local
    VALUE = @Value(GridWidth)
    VARNAME = varRenderSize
    -> CoordinateSystemExtractor
CoordinateSystemExtractor
    CRDSYS_ATTR = __coordsys
    -> CoordinateSystemDescriptionConverter
CoordinateSystemDescriptionConverter
    DIRECTION_LONG = Convert From FME Representation
    KIND_LONG = EPSG Number
    SRC = __coordsys
    VAL_ATTR = __coordsys_epsg
    -> Tester
Tester
    BOOL_OP = OR
    TEST_CLAUSE = TEST @Value(__coordsys_epsg) = 3035
    TEST_MODE = TEST
    PASSED -> Input
    FAILED -> Sampler
Input: Junction
    -> SpatialFilter [Filter]
    -> BoundingBoxAccumulator
BoundingBoxAccumulator
    ACCUM_ATTRS_NAME = Drop Incoming Attributes
    TOPFER_INDEX = No
    BOUNDING_BOX -> AttributeCreator
AttributeCreator
    ATTR_TABLE:
      SET_TO _target_grid_size = 100
      SET_TO _render_size = $(RENDER_SIZE)
    -> BoundsExtractor
BoundsExtractor
    XMAX = _xmax
    XMIN = _xmin
    YMAX = _ymax
    YMIN = _ymin
    ZMAX = _zmax
    ZMIN = _zmin
    -> VariableRetriever
VariableRetriever
    SCOPE = Local
    VALUE_ATTR = _render_size
    VARNAME = varRenderSize
    -> AttributeCreator_6
AttributeCreator_6
    ATTR_TABLE:
      SET_TO _x_render_min = @Evaluate(@int32(@floor(@Value(_xmin)/@Value(_render_size))*@Value(_render_size)))
      SET_TO _y_render_min = @Evaluate(@int32(@floor(@Value(_ymin)/@Value(_render_size))*@Value(_render_size)))
      SET_TO _x_render_max = @Evaluate(@int32(@ceil(@Value(_xmax)/@Value(_render_size))*@Value(_render_size)))
      SET_TO _y_render_max = @Evaluate(@int32(@ceil(@Value(_ymax)/@Value(_render_size))*@Value(_render_size)))
    -> Cloner
Cloner
    COPIES = (@Value(_x_render_max)-@Value(_x_render_min))/@Value(_render_size)
    COPYATT = _render_col
    COPY -> Cloner_2
Cloner_2
    COPIES = (@Value(_y_render_max)-@Value(_y_render_min))/@Value(_render_size)
    COPYATT = _render_row
    COPY -> 2DBoxReplacer
2DBoxReplacer
    MAXXVALATTR = @Value(_x_render_min) + (@Value(_render_col) + 1) * @Value(_render_size)
    MAXYVALATTR = @Value(_y_render_min) + (@Value(_render_row) + 1) * @Value(_render_size)
    MINXVALATTR = @Value(_x_render_min) + @Value(_render_col)*@Value(_render_size)
    MINYVALATTR = @Value(_y_render_min) + @Value(_render_row) * @Value(_render_size)
    BOX -> AttributeKeeper
AttributeKeeper
    CREATE_BULK_MODE_FEATURES = No
    -> BoundsExtractor_2
BoundsExtractor_2
    XMAX = _xmax
    XMIN = _xmin
    YMAX = _ymax
    YMIN = _ymin
    ZMAX = _zmax
    ZMIN = _zmin
    -> AttributeRounder
AttributeRounder
    PLACES = 0
    ROUND_TYPE = Nearest
    SRC_ATTRS = _ymax _xmax _xmin _ymin
    -> SpatialFilter [Candidate]
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> GridCells (output)
GridCells (output)
Sampler
    RATE = 1
    SAMPLE_MODE = No
    SAMPLE_TYPE_LONG = First N Features
    SAMPLED -> Failed (output)
Failed (output)

FME custom transformer VertexExtractor
Description
Extracts all vertices from input geometries and outputs them as 3D Points.
When a vertex is 2D Point, its Z value is set to the value which is given as a user parameter. If the Z value is not specified, 2D points will be returned.
Input Ports 
Input is the data containing coordinates that you would like to turn into vertices. If the source feature is a donut polygon or an aggregate, then this transformer will decompose the feature into its components before breaking them up.
Additionally all point features receive the attributes _feature_number and _vertex_number which, in combination, are unique for every source feature and, respectively, its parts.
The _part_number indicates whether the resulting point was derived from a donut polygon or an aggregate. If a donut or an aggregate was the origin, the _part_number is 0 for the first part and 1 or greater for all other parts. The _part_number is 0 in case of simple features.
Note: If you don't need to know the part numbers, you can also use the Chopper transformer which comes with FME. Setting Maximum Vertices to 1 in the Chopper exposes feature vertices. 
Output Ports 
Output is the point(s) that were created from the transformer. Each resulting point inherits all attributes from its source feature.
Parameters 
When a vertex is 2D Point, its Z value is set to the value which is given as a user parameter. If the Z value is not specified, 2D points will be returned. 
Z Value for 2D Point (optional): Optional parameter to set a Z value on all vertices. Leave blank to keep 2D points.

Parameters:
- DEFAULT_Z_VALUE =

Input (input)
    -> Deaggregator
Note: If input feature consists of aggregates, / split it into "simple" features
Deaggregator
    ATTR_ACCUM_MODE = Merge List Attributes
    ATTR_CONFLICT_RES = Use List Attribute Values
    EXPLODE_INSTANCES = No
    LIST_ATTR_MODE_LOOKUP = LEAN
    MODE = Flatten One Level
    PART_NUMBER_FIELD = _part_number
    SPLIT_COMPOSITES = Yes
    DEAGGREGATED -> Counter
Counter
    CNT_ATTR = _feature_number
    DOMAIN = counter
    SCOPE = Local
    START = 0
    -> CoordinateConcatenator
Note: Get concatenated coordinates string
CoordinateConcatenator
    COORDINATES_TO_INCLUDE_DIS = X Z Y
    COORD_ATTR = _coordinates
    COORD_DELIM = \
    ELEMENT_DELIM = ,
    -> AttributeSplitter
Note: Split the concatenated coordinates string / to each coordinate and make a list of those
AttributeSplitter
    ATTR_NAME = _coordinates
    DELIMITER = \
    DROP_EMPTY_PARTS = No
    LIST_NAME = _coordinate
    TRIM_OPTION = Both
    -> DimensionExtractor
Note: Extracts dimension, 3 or 2
DimensionExtractor
    DIM_ATTR = _dimension
    -> GeometryRemover
Note: Remove all geometries to prevent / creating many copies of geometry objects / before exploding the coordinate list. / this is very important for the memory usage efficiency.
GeometryRemover
    -> ListExploder
Note: Explode the coordinate list / into every vertex coordinate
ListExploder
    ATTR_ACCUM_MODE = Merge List Attributes
    ATTR_CONFLICT_RES = Use List Attribute Values
    INDEX_ATTR = _element_index
    LIST_ATTR = _coordinate{}
    ELEMENTS -> AttributeSplitter_1
Note: Change each vertex coordinate / to list structure containing [x,y,(z)]
AttributeSplitter_1
    ATTR_NAME = _coordinate
    DELIMITER = ,
    DROP_EMPTY_PARTS = No
    LIST_NAME = _list
    TRIM_OPTION = Both
    -> TestFilter
Note: Divide the work flow according to the dimension / and expose the list elements i.e. x,y.(z)
TestFilter
    DEFAULT_VALUE = <UNFILTERED>
    TEST_LIST = TEST_CLAUSE,"TEST @Value(_dimension) = 3",TEST_LIST,"&_dimension,=,3",TEST_MODE,Automatic,BOOL_OP,OR,_dimension = 3,TEST_CLAUSE,"TEST @Value(_dimension) = 2",TEST_LIST,"&_dimension,=,2",TEST_MODE,Automatic,BOOL_OP,OR,_dimension = 2
    _dimension = 3 -> AttributeExposer
    _dimension = 2 -> ParameterFetcher
AttributeExposer
    ATTR_LIST = _list{0},_list{1}
    -> AttributeManager
Note: When the dimension is 2 and default z is set, / set default value to _list{2} i.e. z. / the default value is given as a parameter
ParameterFetcher
    ATTR_LIST = _list{2} {$(DEFAULT_Z_VALUE)}
    -> AttributeManager
AttributeManager
    ATTR_TABLE:
      REMOVE _dimension
      RENAME_SET_VALUE _element_index > _vertex_number
      RENAME_SET_VALUE _list{0} > _x
      RENAME_SET_VALUE _list{1} > _y
      RENAME_SET_VALUE _list{2} > _z
      REMOVE _coordinate
      REMOVE _coordinates
      REMOVE _list{}
    -> VertexCreator
Note: Finally, create point from x,y,z
VertexCreator
    MEASURE_TYPE = Continuous
    MODE_NAME = Replace with Point
    XVAL = @Value(_x)
    YVAL = @Value(_y)
    ZVAL = @Value(_z)
    -> Point (output)
Point (output)
