FME workspace VectorToGridV2Databricks.fmw
Title: Vector2Grid
Description: This workspace will take any ESRI Shapefile as input and produce gridded csv files.
The workspace will first analyze the bounds of the source data and submit subjobs in order to process the data in tiles.
The columns in the resulting csv should be x y GRIDNUM + exact spelling of fields in in source shapefile.
Parameters:
    GRIDSIZE Size in source coordinate system units 
    OUTPUT_FOLDER "C:\Temp\vectortogrid" 
    PASSWORD "********" 
    Parameters that will be used when submitted as a subprocess: 
    SUBPROCESS "NO" 
    MINX "" 
    MINY "" 
    MAXX "" 
    MAXY "" 
    OUTPUT_FEATURETYPE_BASENAME ""

Parameters:
- ENABLE_POST_PROCESSING =
- FME_JOB_ID = 0
- FME_SECURITY_USER = segerstedt
- FME_SERVER_HOST = http://fmebatch.discomap.eea.europa.eu
- FME_SHAREDRESOURCE_DATA = //mynah/fmeservershare/resources/data
- FME_USER_PARAM_PRIVATE_GRP =
- FileId =
- PC_MAPPING =
- RENDER_SIZE =
- WORKSPACE_REPOSITORY_NAME =

SQLCreator
    DATASET = CubeManager
    EXPOSED_ATTRIBUTE_LIST = CubeDimensionId FileId SourceFile CubeShortName GridTypesShortName SourceFileReceived
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = CubeManager
    MSSQL_ADO_QUERY_FEATURE_TYPES_FOR_MERGE_FILTERS = Yes
    SQL_STATEMENT:
      select  CubeDimensions.CubeDimensionId,
              GridTypes.name as GridTypesShortName,
              CubeDimensions.Name as CubeShortName,
              Files.FileId,
              Files.SourceFile,
              Files.SourceFileReceived
      from CubeDimensions
      inner join Files on CubeDimensions.CubeDimensionId = Files.CubeDimensionId
      inner join GridTypes on GridTypes.GridTypeId = Cubedimensions.GridTypeId
      where FileId = $(FileId)
      --and FmeConversionProcess = '$(WORKSPACE_NAME)'
    RESULT -> AttributeCreator_13
    <REJECTED> -> AttributeCreator_10
AttributeCreator_14
    ATTR_TABLE:
      SET_TO MessageString = Store file info falied
      SET_TO TransformerPath = $(WORKSPACE_NAME)\Store_File_info_2
    -> AttributeCreator_10_OUTPUT_-__TYPE_ERROR_2
Note: Find Dimension temp path
SQLExecutor
    COMBINE_ATTRS = Keep Initiator Attributes if Conflict
    COMBINE_GEOM = Initiator Geometry Only
    DATASET = CubeManager
    EXPOSED_ATTRIBUTE_LIST = __TempDimensionLocationPath
    FORMAT = MSSQL_ADO
    MSSQL_ADO_COMMAND_TIMEOUT = 30
    MSSQL_ADO_CREATE_FEATURE_TABLES_FROM_DATA = Yes
    MSSQL_ADO_NAMED_CONNECTION = CubeManager
    MSSQL_ADO_QUERY_FEATURE_TYPES_FOR_MERGE_FILTERS = Yes
    SQL_STATEMENT:
      select AttributeValue as __TempDimensionLocationPath
      from dbo.GeneralInfo
      where AttributeName = 'DimensionTempLocation'
    RESULT -> DateFormatter
    <REJECTED> -> AttributeCreator_11
AttributeCreator_11
    ATTR_TABLE:
      SET_TO MessageString = Initial SQL Failed
      SET_TO TransformerPath = $(WORKSPACE_NAME)\SQLExecutor
    -> AttributeCreator_10_OUTPUT_-__TYPE_ERROR_2
DateFormatter
    DATE_ATTR = SourceFileReceived
    FMT = %Y_%m_%d
    INVALID_DATE_VALUE = _FME_NO_OP_
    SRCFMT = %Y%m%d%H%M%S.000
    -> VariableSetter
VariableSetter
    SCOPE = Global
    VALUE = @Value(CubeShortName)_@Value(GridTypesShortName)_@Value(SourceFileReceived).csv
    VARNAME = originalFileName
    -> VariableSetter_2
VariableSetter_2
    SCOPE = Global
    VALUE = @Value(__TempDimensionLocationPath)
    VARNAME = TempDimensionLocationPath
    -> ValidateZipContent
    -> VariableSetter_OUTPUT
AttributeCreator_8
    ATTR_TABLE:
      SET_TO MessageString = Error: @Value(_reader_error).
        WorkSpace: $(WORKSPACE_NAME)
        Transformer name: SQLExecutor_3
      SET_TO TransformerPath = $(WORKSPACE_NAME)\SQLExecutor_3
    -> AttributeCreator_10_OUTPUT_-__TYPE_ERROR_2
AttributeCreator_7
    ATTR_TABLE:
      SET_TO MessageString = Error: @Value(_reader_error).
        WorkSpace: $(WORKSPACE_NAME)
        Transformer name: SQLExecutor_4
      SET_TO TransformerPath = $(WORKSPACE_NAME)\SQLExecutor_4
    -> AttributeCreator_10_OUTPUT_-__TYPE_ERROR_2
Note: Reset the database and provide the job_id so log information can be found easily.
TestFilter
    DEFAULT_VALUE = <UNFILTERED>
    TEST_LIST = "BOOL_OP,OR,COMPOSITE_TEST,""""""1"""""",TEST_CLAUSE,TEST @Value(file_type) = shp",shp,"BOOL_OP,OR,COMPOSITE_TEST,""""""1"""""",TEST_CLAUSE,TEST @Value(file_type) = gdb",gdb,"BOOL_OP,OR,COMPOSITE_TEST,""""""1"""""",TEST_CLAUSE,TEST @Value(file_type) = gpkg",gpkg
    shp -> FeatureReaderSHP [INITIATOR]
    gdb -> FeatureReaderGDB [INITIATOR]
    gpkg -> FeatureReaderGPKG [INITIATOR]
FeatureMerger
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> FilteringGridAccumulator
Aggregator_2
    ACCUM_ATTRS_NAME = Drop Incoming Attributes
    GROUP_BY = $(FileId)
    MODE = Attributes Only
    ORDERED = No
    SEP = ,
    AGGREGATE -> AttributeCreator_INFO_2
AttributeCreator_INFO_2
    ATTR_TABLE:
      SET_TO MessageString = GridCells output
      SET_TO TransformerPath = MASTER_PROCESS: Execute several sub processes\FilteringGridAccumulator
    -> AttributeKeeper
AttributeCreator_Error
    ATTR_TABLE:
      SET_TO MessageString = @Value(_Error)
      SET_TO TransformerPath = MASTER_PROCESS: Execute several sub processes\FilteringGridAccumulator
    -> TYPE_ERROR_2 [off]
AttributeCreator_6
    ATTR_TABLE = SET_TO TransformerPath = MASTER_PROCESS: Execute several sub processes\SQLExecutor_Error_2
    -> TYPE_ERROR_2
AttributeKeeper
    CREATE_BULK_MODE_FEATURES = No
    KEEP_ATTRS = TransformerPath,MessageString,FileId
    -> TYPE_INFO
TYPE_INFO: AttributeCreator
    ATTR_TABLE = SET_TO MessageType = INFO
    -> AttributeCreator_2
AttributeCreator_9
    ATTR_TABLE:
      SET_TO MessageString = Error: @Value(_reader_error).
        WorkSpace: $(WORKSPACE_NAME)
        Transformer name: SQLExecutor_Accepted
      SET_TO TransformerPath = $(WORKSPACE_NAME)\SQLExecutor_Accepted
    -> AttributeCreator_10_OUTPUT_-__TYPE_ERROR_2
Note: FeatureMerger : Supplier
VariableSetter_OUTPUT: Junction
AttributeCreator_10
    ATTR_TABLE:
      SET_TO MessageString = Initial SQL Failed
      SET_TO TransformerPath = $(WORKSPACE_NAME)\SQLCreator
    -> AttributeCreator_10_OUTPUT_-__TYPE_ERROR_2
AttributeCreator_10_OUTPUT_-__TYPE_ERROR_2: Junction
    -> TYPE_ERROR_2
TYPE_ERROR_2: Junction
    -> TYPE_ERROR
TYPE_ERROR: AttributeCreator
    ATTR_TABLE = SET_TO MessageType = ERROR
    -> AttributeKeeper_2
AttributeKeeper_2
    CREATE_BULK_MODE_FEATURES = No
    KEEP_ATTRS = TransformerPath,MessageType,MessageString,FileId
    -> AttributeCreator_2
AttributeCreator_2
    ATTR_TABLE = SET_TO ObjectProcessed = Dimension
    -> JediLogWritter
JediLogWritter
    FILEID = $(FileId)
    MESSAGESTRING = @Value(MessageString)
    MESSAGETYPE = @Value(MessageType)
    OBJECTPROCESSED = @Value(ObjectProcessed)
    SQLServerConn = CubeManager
    TRANSFORMERPATH = $(WORKSPACE_NAME)\STEP1:SOURCE FORMAT TO GRID\@Value(TransformerPath)
    -> Tester_2
Tester_2
    BOOL_OP = OR
    COMPOSITE_TEST = 1
    TEST_CLAUSE = TEST @Value(MessageType) = ERROR
    TEST_MODE = TEST
    PASSED -> Terminator_4
Terminator_4
    MESSAGE = Translation Terminated: @Value(MessageString)

Bookmark: Tell DB we are executing the job
AttributeCreator_13
    ATTR_TABLE = SET_TO _FME_JOB_ID = FME_CONDITIONAL:DEFAULT_VALUE'$(FME_JOB_ID)'BOOL_OP;AND;COMPOSITE_TEST;<Unused>;TEST $(FME_JOB_ID) ATTRIBUTE_IS_MISSING _FME_BLANK_STRING_;TEST $(FME_JOB_ID) NOT_ATTRIBUTE_HAS_VALUE _FME_BLANK_STRING_'-1'FME_NUM_CONDITIONS2___
    -> Store_File_Info_2 [INITIATOR]
Store_File_Info_2: SQLExecutor
    COMBINE_ATTRS = Result Attributes Only
    COMBINE_GEOM = Initiator Geometry Only
    DATASET = CubeManager
    FORMAT = MSSQL_ADO
    MSSQL_ADO_COMMAND_TIMEOUT = 30
    MSSQL_ADO_NAMED_CONNECTION = CubeManager
    MSSQL_ADO_QUERY_FEATURE_TYPES_FOR_MERGE_FILTERS = Yes
    SQL_STATEMENT:
      Update dbo.Files
          set [FMEJobIdDimensionProcess]=@Value(_FME_JOB_ID)
      where FileId = @Value(FileId)
    INITIATOR -> CleanUpBlob_2
    <REJECTED> -> AttributeCreator_14
CleanUpBlob_2
    AZUREDIMENSIONFILE = Dimensions/@Value(CubeShortName)_@Value(FileId)
    FILEID = @Value(FileId)
    NAME = @Value(CubeShortName)
    Initiator -> JediLogWritter_startjob
JediLogWritter_startjob
    FILEID = $(FileId)
    MESSAGESTRING = Conversion started
    MESSAGETYPE = INFO
    OBJECTPROCESSED = Dimension
    SQLServerConn = CubeManager
    TRANSFORMERPATH = $(WORKSPACE_NAME)\VectorToGridV2
    -> SQLExecutor [INITIATOR]

Bookmark: Find out if the content is correct.
ValidateZipContent
    FILEID = @Value(FileId)
    SOURCEFILE = @Value(SourceFile)
    Continue -> SQLExecutor_Accepted [INITIATOR]
    Fields -> Aggregator
    Fields -> SQLExecutor_3 [INITIATOR]
    Error -> SQLExecutor_Error [INITIATOR]
SQLExecutor_3
    COMBINE_ATTRS = Result Attributes Only
    COMBINE_GEOM = Initiator Geometry Only
    DATASET = CubeManager
    FORMAT = MSSQL_ADO
    MSSQL_ADO_COMMAND_TIMEOUT = 30
    MSSQL_ADO_CREATE_FEATURE_TABLES_FROM_DATA = Yes
    MSSQL_ADO_NAMED_CONNECTION = CubeManager
    MSSQL_ADO_QUERY_FEATURE_TYPES_FOR_MERGE_FILTERS = Yes
    SQL_STATEMENT = exec dbo.InsertFieldIntoDimensionFields @Value(FileId),'@Value(FieldName)','@Value(FieldName)','@Value(FieldType)',@Value(IgnoreField),'@Value(Title)','@Value(Description)',@Value(FieldOrder),NULL
    <REJECTED> -> AttributeCreator_8
SQLExecutor_Error
    COMBINE_ATTRS = Result Attributes Only
    COMBINE_GEOM = Initiator Geometry Only
    DATASET = CubeManager
    FORMAT = MSSQL_ADO
    MSSQL_ADO_COMMAND_TIMEOUT = 30
    MSSQL_ADO_NAMED_CONNECTION = CubeManager
    MSSQL_ADO_QUERY_FEATURE_TYPES_FOR_MERGE_FILTERS = Yes
    SQL_STATEMENT:
      Update dbo.Files
          set Validated = 0,
              ErrorMessages = '@Value(ErrorMessage)',
              FMEJobIdValidator=@Value(FMEJobIdValidator)
      where FileId = @Value(FileId)
Aggregator
    ACCUM_ATTRS_NAME = Use Attributes From One Feature
    AGGREGATE_TYPE = Homogeneous Collection (If Possible)
    CONCAT_ATTRS = FieldName
    GROUP_BY = FileId
    MODE = Geometry - Assemble One Level
    ORDERED = No
    SEP = ','
    AGGREGATE -> SQLExecutor_4 [INITIATOR]
SQLExecutor_4
    COMBINE_ATTRS = Result Attributes Only
    COMBINE_GEOM = Initiator Geometry Only
    DATASET = CubeManager
    FORMAT = MSSQL_ADO
    MSSQL_ADO_COMMAND_TIMEOUT = 30
    MSSQL_ADO_CREATE_FEATURE_TABLES_FROM_DATA = Yes
    MSSQL_ADO_NAMED_CONNECTION = CubeManager
    MSSQL_ADO_QUERY_FEATURE_TYPES_FOR_MERGE_FILTERS = Yes
    SQL_STATEMENT = DELETE dbo.Fields WHERE FileId = @Value(FileId) and FieldName not in ('@Value(FieldName)')
    <REJECTED> -> AttributeCreator_7
SQLExecutor_Accepted
    COMBINE_ATTRS = Result Attributes Only
    COMBINE_GEOM = Initiator Geometry Only
    DATASET = CubeManager
    FORMAT = MSSQL_ADO
    MSSQL_ADO_COMMAND_TIMEOUT = 30
    MSSQL_ADO_NAMED_CONNECTION = CubeManager
    MSSQL_ADO_QUERY_FEATURE_TYPES_FOR_MERGE_FILTERS = Yes
    SQL_STATEMENT:
      Update dbo.Files
          set Validated = 1,
              FMEJobIdValidator=@Value(FMEJobIdValidator)
      where FileId = @Value(FileId)
    INITIATOR -> VariableSetter_3
    <REJECTED> -> AttributeCreator_9
VariableSetter_3
    SCOPE = Global
    VALUE = @Value(fme_feature_type)
    VARNAME = feature_type
    -> TestFilter

Bookmark: Read file
FeatureReaderSHP
    ATTR_ACCUM_MODE = Only Use Result
    COMBINE_GEOM = Use Result
    DATASET = @Value(fme_feature_type)
    ESRISHAPE_CHECK_NUMERIC_FIELDS = yes
    ESRISHAPE_DISSOLVE_HOLES = no
    ESRISHAPE_ENCODING = utf-8
    ESRISHAPE_MEASURES_AS_Z = no
    ESRISHAPE_NUMERIC_TYPE_ATTRIBUTE_HANDLING = STANDARD_TYPES
    ESRISHAPE_REPORT_BAD_GEOMETRY = no
    ESRISHAPE_SIMPLE_DONUT_GEOMETRY = simple
    ESRISHAPE_TRIM_PRECEDING_SPACES = yes
    ESRISHAPE_UPPER_CASE_ATTR_NAMES = No
    ESRISHAPE_USE_SEARCH_ENVELOPE = NO
    FORMAT = ESRISHAPE
    INTERACT = <No Spatial Filter>
    OUTPUT_FEATURES_DISPLAY = Schema and Data Features
    <OTHER> -> FeatureMerger [REQUESTOR]
    INITIATOR -> FeatureMerger [SUPPLIER]
    <REJECTED> -> AttributeCreator_12
FeatureReaderGDB
    ATTR_ACCUM_MODE = Only Use Result
    COMBINE_GEOM = Use Result
    DATASET = @Value(fme_feature_type)
    FORMAT = GEODATABASE_FILE
    GEODATABASE_FILE_ALIAS_MODE = NONE
    GEODATABASE_FILE_CACHE_MULTIPATCH_TEXTURES = yes
    GEODATABASE_FILE_CHECK_SIMPLE_GEOM = no
    GEODATABASE_FILE_CREATE_FEATURE_TABLES_FROM_DATA = Yes
    GEODATABASE_FILE_FEATURE_READ_MODE = Features
    GEODATABASE_FILE_IGNORE_NETWORK_INFO = yes
    GEODATABASE_FILE_IGNORE_RELATIONSHIP_INFO = yes
    GEODATABASE_FILE_MERGE_FEAT_LINKED_ANNOS = no
    GEODATABASE_FILE_QUERY_FEATURE_TYPES_FOR_MERGE_FILTERS = Yes
    GEODATABASE_FILE_RESOLVE_DOMAINS = no
    GEODATABASE_FILE_RESOLVE_SUBTYPE_NAMES = yes
    GEODATABASE_FILE_SPLIT_COMPLEX_ANNOS = no
    GEODATABASE_FILE_SPLIT_COMPLEX_EDGES = no
    GEODATABASE_FILE_SPLIT_MULTI_PART_ANNOS = no
    GEODATABASE_FILE_STRIP_GUID_GLOBALID_BRACES = no
    GEODATABASE_FILE_TRANSLATE_SPATIAL_DATA_ONLY = no
    GEODATABASE_FILE_USE_SEARCH_ENVELOPE = NO
    INTERACT = <No Spatial Filter>
    OUTPUT_FEATURES_DISPLAY = Schema and Data Features
    <OTHER> -> FeatureMerger [REQUESTOR]
    INITIATOR -> FeatureMerger [SUPPLIER]
    <REJECTED> -> AttributeCreator_12
FeatureReaderGPKG
    ATTR_ACCUM_MODE = Only Use Result
    COMBINE_GEOM = Use Result
    DATASET = @Value(fme_feature_type)
    FORMAT = OGCGEOPACKAGE
    INTERACT = <No Spatial Filter>
    OGCGEOPACKAGE_ENCODE_FEATURE_TYPE_AND_ATTR_NAMES = YES
    OGCGEOPACKAGE_ENFORCE_FOREIGN_KEY_INTEGRITY = YES
    OGCGEOPACKAGE_OPEN_SINGLE_RASTER_AS_SUBDATASET = YES
    OGCGEOPACKAGE_QUERY_FEATURE_TYPES_FOR_MERGE_FILTERS = Yes
    OGCGEOPACKAGE_READ_BOOLEANS_AS_YES_NO = YES
    OGCGEOPACKAGE_READ_NULLS = YES
    OGCGEOPACKAGE_USE_SEARCH_ENVELOPE = NO
    OUTPUT_FEATURES_DISPLAY = Schema and Data Features
    <OTHER> -> FeatureMerger [REQUESTOR]
    INITIATOR -> FeatureMerger [SUPPLIER]
    <REJECTED> -> AttributeCreator_12
AttributeCreator_12
    ATTR_TABLE:
      SET_TO MessageString = Error: @Value(_reader_error).
        WorkSpace: $(WORKSPACE_NAME)
        Transformer name: FeatureReader
      SET_TO TransformerPath = $(WORKSPACE_NAME)\FeatureReader
    -> AttributeCreator_10_OUTPUT_-__TYPE_ERROR_2

Bookmark: MASTER_PROCESS: Execute several sub processess
FilteringGridAccumulator
    RENDER_SIZE = $(RENDER_SIZE)
    GridCells -> SQLExecutor_2 [INITIATOR]
    GridCells -> Aggregator_2
    Failed -> SQLExecutor_Error_2 [INITIATOR]
    Failed -> AttributeCreator_Error
SQLExecutor_Error_2
    COMBINE_ATTRS = Result Attributes Only
    COMBINE_GEOM = Initiator Geometry Only
    DATASET = CubeManager
    FORMAT = MSSQL_ADO
    MSSQL_ADO_COMMAND_TIMEOUT = 30
    MSSQL_ADO_NAMED_CONNECTION = CubeManager
    MSSQL_ADO_QUERY_FEATURE_TYPES_FOR_MERGE_FILTERS = Yes
    SQL_STATEMENT:
      Update dbo.Files
          set Validated = 0,
              ErrorMessages = '@Value(_Error)',
              FMEJobIdValidator=$(FME_JOB_ID)
      where FileId = $(FileId)
    INITIATOR -> AttributeCreator_6
    <REJECTED> -> AttributeCreator_6
SQLExecutor_2
    COMBINE_ATTRS = Keep Initiator Attributes if Conflict
    COMBINE_GEOM = Initiator Geometry Only
    DATASET = CubeManager
    EXPOSED_ATTRIBUTE_LIST = CubeDimensionId CubeShortName FileId GridSize OutPutFolder SourceFile SourceFileReceived AzureSourceFile
    FORMAT = MSSQL_ADO
    MSSQL_ADO_COMMAND_TIMEOUT = 30
    MSSQL_ADO_CREATE_FEATURE_TABLES_FROM_DATA = Yes
    MSSQL_ADO_NAMED_CONNECTION = CubeManager
    MSSQL_ADO_QUERY_FEATURE_TYPES_FOR_MERGE_FILTERS = Yes
    SQL_STATEMENT:
      select  CubeDimensions.CubeDimensionId,
              XCellSpacing        as GridSize,
              CubeDimensions.Name as CubeShortName,
              Files.FileId,
              Files.SourceFile,
              Files.SourceFileReceived,
              (select AttributeValue from [dbo].[GeneralInfo] where AttributeName = 'DimensionTempLocation') as OutPutFolder,
              Files.AzureSourceFile
      from CubeDimensions
      inner join Files on CubeDimensions.CubeDimensionId = Files.CubeDimensionId
      inner join GridTypes on GridTypes.GridTypeId = Cubedimensions.GridTypeId
      where
       FileId = $(FileId)
    RESULT -> VariableRetriever
VariableRetriever
    SCOPE = Global
    VALUE_ATTR = fme_feature_type
    VARNAME = feature_type
    -> AttributeCreator
AttributeCreator
    ATTR_TABLE:
      SET_TO OutPutFolder = @Value(OutPutFolder)/@Value(CubeShortName)
      SET_TO AzureDimensionFile = Dimensions/@Value(CubeShortName)_@Value(FileId)
      SET_TO AzureSourceFile = https://cwsblobstorage01.blob.core.windows.net/cwsblob01/@Value(AzureSourceFile)
    -> DeleteFolder [FileName]
DeleteFolder: FileSystemDeleteMoveCopyExist
    Action = RMDIR
    FILEINPUT = @Value(OutPutFolder)
    Success -> MakeDirectory [FileName]
    NotFound -> MakeDirectory [FileName]
    Failed -> SQLExecutor_Error_3 [INITIATOR]
Note: Write Error in Database
SQLExecutor_Error_3
    COMBINE_ATTRS = Result Attributes Only
    COMBINE_GEOM = Initiator Geometry Only
    DATASET = CubeManager
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = CubeManager
    MSSQL_ADO_QUERY_FEATURE_TYPES_FOR_MERGE_FILTERS = Yes
    SQL_STATEMENT:
      Update dbo.Files
          set Validated = 0,
              ErrorMessages = 'Internal Error - Filesystem',
              FMEJobIdValidator=$(FME_JOB_ID)
      where FileId = $(FileId)
    INITIATOR -> AttributeCreator_4
    <REJECTED> -> AttributeCreator_4
AttributeCreator_4
    ATTR_TABLE = SET_TO TransformerPath = MASTER_PROCESS: Execute several sub processes\SQLExecutor_Error_3
    -> TYPE_ERROR_2
MakeDirectory: FileSystemDeleteMoveCopyExist
    Action = MKDIR
    FILEINPUT = @Value(OutPutFolder)
    Success -> FMEServerJobSubmitter_2
    Failed -> FMEServerJobSubmitter_2
    Failed -> AttributeCreator_Error_2
AttributeCreator_Error_2
    ATTR_TABLE:
      SET_TO MessageString = Make directory failed
      SET_TO TransformerPath = MASTER_PROCESS: Execute several sub processes\MakeDirectory
    -> TYPE_ERROR_2
Note: Execute VectorToGridV2_Parts.fmw
FMEServerJobSubmitter_2
    BLOCKING = Yes
    PRIORITY = 150
    PROCESSING_MODE = In Parallel
    REPOSITORY = CubeSubProcessess
    SERVER_CONNECTION = diaz FME Server
    WORKSPACE_NAME = VectorToGridV2_PartsDatabricks.fmw
    WORKSPACE_PARAMETERS = SOURCE_SHAPE_DATASET list @Value(SourceFile) GRIDSIZE string @Value(GridSize) MINX string @Value(_xmin) MINY string @Value(_ymin) MAXX string @Value(_xmax) MAXY string @Value(_ymax) OUTPUT_FOLDER string @Value(OutPutFolder) OUTPUT_FEATURETYPE_BASENAME string @Value(CubeShortName) FileId string @Value(FileId) File_Type string @Value(file_type)
    JOB_SUCCEEDED -> FMEServerJobWaiter_Succeeded
    JOB_FAILED -> AttributeCreator_3
    JOB_FAILED -> FMEServerJobWaiter_Failed
    <REJECTED> -> AttributeCreator_5

Bookmark: POST_PROCESSING : Wait for all processess to finish
AttributeCreator_5
    ATTR_TABLE:
      SET_TO TransformerPath = MASTER_PROCESS: Execute several sub processes\FMEServerJobSubmitter_2
      SET_TO MessageString = Impossible to call the FME  process VectorToGridV2_Parts.fmw
    -> FMEServerJobWaiter_Succeeded
FMEServerJobWaiter_Succeeded: Logger
    MAXCOORDS = 20
    MAXFEATS = 20
    MESSAGE = Feature is:
    LOGGED -> FeatureHolder_2
    LOGGED -> AttributeKeeper
AttributeCreator_3
    ATTR_TABLE:
      SET_TO TransformerPath = MASTER_PROCESS: Execute several sub processes\FMEServerJobSubmitter_2
      SET_TO MessageString = FME  process VectorToGridV2_Parts.fmw failed, Jobid: @Value(_job_id)
    -> TYPE_ERROR_2
FMEServerJobWaiter_Failed: Logger
    MAXCOORDS = 20
    MAXFEATS = 20
    MESSAGE = Feature is:
    LOGGED -> TYPE_ERROR_2

Bookmark: CUBEMANAGER DB UPDATE: Store meta information
FeatureHolder_2
    -> Sampler
Sampler
    RATE = 1
    SAMPLE_MODE = No
    SAMPLE_TYPE_LONG = First N Features
    SAMPLED -> Store_File_Info [INITIATOR]
    SAMPLED -> Aggregator_3
    SAMPLED -> ZipArchiver [off]
Aggregator_3
    ACCUM_ATTRS_NAME = Drop Incoming Attributes
    GROUP_BY = $(FileId)
    MODE = Attributes Only
    ORDERED = No
    SEP = ,
    AGGREGATE -> AttributeCreator_INFO_3
AttributeCreator_INFO_3
    ATTR_TABLE:
      SET_TO MessageString = FME  process VectorToGridV2_Parts.fmw Succeeded
      SET_TO TransformerPath = MASTER_PROCESS: Execute several sub processes\FMEServerJobSubmitter_2
    -> AttributeKeeper
Note: Set status to 1 and store path to dimension files.
Store_File_Info: SQLExecutor
    COMBINE_ATTRS = Result Attributes Only
    COMBINE_GEOM = Initiator Geometry Only
    DATASET = CubeManager
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = CubeManager
    MSSQL_ADO_QUERY_FEATURE_TYPES_FOR_MERGE_FILTERS = Yes
    SQL_STATEMENT:
      Update dbo.Files
          set [DimensionFile] = '@Value(OutPutFolder)',
              [DimensionFileCreated]=getdate(),
              [AzureDimensionFile] = 'Dimensions/@Value(CubeShortName)_@Value(FileId)',
              [AzureDimensionUploaded] = getdate(),
              [FMEJobIdDimensionProcessStatus]=1,
              ErrorMessages = Null
      where FileId = @Value(FileId)
    INITIATOR -> AttributeKeeper
    <REJECTED> -> TYPE_ERROR_2

Bookmark: IN Order to avoid uploading errors, build a zip file that conatins all .csv.gz files
ZipArchiver
    COMPRESSION_LEVEL = -1
    FILE_PATH = @Value(OutPutFolder)
    MODE = APPEND
    ZIP_PATH = @Value(OutPutFolder)/Files.zip
    -> Aggregator_3 [off]
    -> FeatureReader_2 [INITIATOR]

Bookmark: Delete csv.gz files
FeatureReader_2
    ATTR_ACCUM_MODE = Merge Initiator and Result
    ATTR_CONFLICT_RES = Use Result
    COMBINE_GEOM = Use Result
    DATASET = @Value(OutPutFolder)
    FORMAT = PATH
    OUTPUT_FEATURES_DISPLAY = Schema and Data Features
    PATH_GLOB_PATTERN = *.csv.gz
    PATH_NO_EMPTY_PROPERTIES = YES
    PATH_RECURSE_DIRECTORIES = NO
    PATH_RETRIEVE_FILE_PROPERTIES = NO
    PATH_TYPE = FILE
    <OTHER> -> AttributeExposer
AttributeExposer
    ATTR_LIST = path_directory_windows,path_filename
    -> AttributeCreator_15
AttributeCreator_15
    ATTR_TABLE = SET_TO DimensionFile = @Value(path_directory_windows)@Value(path_filename)
    -> FileSystemDeleteMoveCopyExist [FileName]
FileSystemDeleteMoveCopyExist
    Action = DELETE
    FILEINPUT = @Value(DimensionFile)
    Success -> Store_File_Info [INITIATOR]
    NotFound -> Store_File_Info [INITIATOR]
    Failed -> Store_File_Info [INITIATOR]

FME custom transformer getFilesNamesInZip_2
Retrieve the file and folder names from a zip file. The transformer is not reading the files itself. It just extracts the stored files.

Parameters:
- sourceZipFile =

zipFile (input)
    -> ParameterFetcher
Note: Retrieves the files from a .zip file and expose those as features.
ParameterFetcher
    ATTR_LIST = sourceZipFile {$(sourceZipFile)}
    -> readZipContentPy
readZipContentPy: PythonCaller
    NEW_ATTRIBUTES = _zipFileContent{}
    PYTHONSOURCE:
      import fmeobjects
      # Template Function interface:
      def processFeature(feature):
          pass

      # Template Class Interface:
      class FeatureProcessor(object):
          def __init__(self):
              pass
          def input(self,feature):
              import zipfile
              # get file name form FME
              myzipfile = feature.getAttribute("sourceZipFile")
              # zipfileContent list that we will send back to FME
              _zipFileContent=[]
              # Open zip file.
              try:
                  zz = zipfile.ZipFile(myzipfile)

                  #zz.printdir()
                  for name in zz.infolist():
                      _zipFileContent.append(name.filename)
                  zz.close()
              except:
                  pass
              # send content back to FME as a list
              feature.setAttribute("_zipFileContent{}",_zipFileContent)
              self.pyoutput(feature)
          def close(self):
              pass
    PYTHONSYMBOL = FeatureProcessor
    -> ListExploder
ListExploder
    INDEX_ATTR = fileCounter
    LIST_ATTR = _zipFileContent{}
    MODE = List Elements and Original Attributes
    LIST_FOUND -> AttributeRenamer
AttributeRenamer
    ATTR_LIST = _zipFileContent,zipFileName,""
    -> FilenamePartExtractor
FilenamePartExtractor
    EXTENSION_ATTR = fileExtension
    SRC_ATTR = @Value(zipFileName)
    -> Files (output)
Files (output)

FME custom transformer FilteringGridAccumulator

Parameters:
- RENDER_SIZE =

Input (input)
    -> CoordinateSystemExtractor
CoordinateSystemExtractor
    CRDSYS_ATTR = __coordsys
    -> CoordinateSystemDescriptionConverter
CoordinateSystemDescriptionConverter
    DIRECTION_LONG = Convert From FME Representation
    KIND_LONG = EPSG Number
    SRC = __coordsys
    VAL_ATTR = __coordsys_epsg
    -> Tester
Tester
    BOOL_OP = OR
    TEST_CLAUSE = TEST @Value(__coordsys_epsg) = 3035
    TEST_MODE = TEST
    PASSED -> Input
    FAILED -> Sampler
Input: Junction
    -> SpatialFilter [Filter]
    -> BoundingBoxAccumulator
BoundingBoxAccumulator
    ACCUM_ATTRS_NAME = Drop Incoming Attributes
    TOPFER_INDEX = No
    BOUNDING_BOX -> AttributeCreator
AttributeCreator
    ATTR_TABLE:
      SET_TO _target_grid_size = 100
      SET_TO _render_size = $(RENDER_SIZE)
    -> BoundsExtractor
BoundsExtractor
    XMAX = _xmax
    XMIN = _xmin
    YMAX = _ymax
    YMIN = _ymin
    ZMAX = _zmax
    ZMIN = _zmin
    -> AttributeCreator_6
AttributeCreator_6
    ATTR_TABLE:
      SET_TO _x_render_min = @Evaluate(@int32(@floor(@Value(_xmin)/@Value(_render_size))*@Value(_render_size)))
      SET_TO _y_render_min = @Evaluate(@int32(@floor(@Value(_ymin)/@Value(_render_size))*@Value(_render_size)))
      SET_TO _x_render_max = @Evaluate(@int32(@ceil(@Value(_xmax)/@Value(_render_size))*@Value(_render_size)))
      SET_TO _y_render_max = @Evaluate(@int32(@ceil(@Value(_ymax)/@Value(_render_size))*@Value(_render_size)))
    -> Cloner
Cloner
    COPIES = (@Value(_x_render_max)-@Value(_x_render_min))/@Value(_render_size)
    COPYATT = _render_col
    COPY -> Cloner_2
Cloner_2
    COPIES = (@Value(_y_render_max)-@Value(_y_render_min))/@Value(_render_size)
    COPYATT = _render_row
    COPY -> 2DBoxReplacer
2DBoxReplacer
    MAXXVALATTR = @Value(_x_render_min) + (@Value(_render_col) + 1) * @Value(_render_size)
    MAXYVALATTR = @Value(_y_render_min) + (@Value(_render_row) + 1) * @Value(_render_size)
    MINXVALATTR = @Value(_x_render_min) + @Value(_render_col)*@Value(_render_size)
    MINYVALATTR = @Value(_y_render_min) + @Value(_render_row) * @Value(_render_size)
    BOX -> AttributeKeeper
AttributeKeeper
    CREATE_BULK_MODE_FEATURES = No
    -> BoundsExtractor_2
BoundsExtractor_2
    XMAX = _xmax
    XMIN = _xmin
    YMAX = _ymax
    YMIN = _ymin
    ZMAX = _zmax
    ZMIN = _zmin
    -> AttributeRounder
AttributeRounder
    PLACES = 0
    ROUND_TYPE = Nearest
    SRC_ATTRS = _ymax _xmax _xmin _ymin
    -> SpatialFilter [Candidate]
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> GridCells (output)
GridCells (output)
Sampler
    RATE = 1
    SAMPLE_MODE = No
    SAMPLE_TYPE_LONG = First N Features
    SAMPLED -> Failed (output)
Failed (output)

FME custom transformer ExtractFileFromZip
Extracts one file form a zip into a local disk. Use this together with the "getMetaDataFromZip" Transformer who tells you whats inside the zip file.
Zipsourcefile: The location towards the zip-file
    sourceFile: The sourcefile inside the zip to be extracted.
    destinationFolder: The destination folder this file should be extracted to.

Parameters:
- DESTINATIONFOLDER =
- SOURCEFILE =
- ZIPSOURCEFILE =

INPUT (input)
    -> CreateOutputFolder [FileName]
CreateOutputFolder: FileSystemDeleteMoveCopyExist
    Action = EXIST
    FILEINPUT = @Value(destinationFolder)
    Success -> unZipPython
unZipPython: PythonCaller
    NEW_ATTRIBUTES = _status
    PYTHONSOURCE:
      import fmeobjects
      import zipfile,os.path
      # Template Function interface:
      def processFeature(feature):
          pass

      # Template Class Interface:
      class FeatureProcessor(object):
          #
          # Extracts one file
          #
          def unzipOneFile(self,source_filename,filename,dest_dir):
              zfile = zipfile.ZipFile(source_filename)
              zfile.extract(filename,dest_dir)

          def __init__(self):
              pass
          def input(self,feature):
              source_filename = feature.getAttribute("zipSourceFile")
              filename = feature.getAttribute("sourceFile")
              dest_dir = feature.getAttribute("destinationFolder")
              #
              status = "success"
              # execute unzip
              #self.unzipOneFile(source_filename,filename,dest_dir)
              try:
                  self.unzipOneFile(source_filename,filename,dest_dir)
              except Exception:
                  status="failed"
                  pass
              # set if successfull
              feature.setAttribute("_status",status)
              self.pyoutput(feature)
          def close(self):
              pass
    PYTHONSYMBOL = FeatureProcessor
    -> TestFilter
TestFilter
    DEFAULT_VALUE = FAILED
    TEST_LIST = BOOL_OP,OR,COMPOSITE_TEST,<Unused>,TEST_CLAUSE,"TEST @Value(_status) = success",SUCCESS
    SUCCESS -> SUCCESS (output)
    FAILED -> RemoveFolder [FileName]
    FAILED -> Failed
SUCCESS (output)
RemoveFolder: FileSystemDeleteMoveCopyExist
    Action = EXIST
    FILEINPUT = @Value(destinationFolder)
    Success -> FAILED (output)
    Failed -> FAILED (output)
FAILED (output)
Failed: Inspector [off]

FME custom transformer getFilesNamesInZip
Retrieve the file and folder names from a zip file. The transformer is not reading the files itself. It just extracts the stored files.

Parameters:
- sourceZipFile =

zipFile (input)
    -> ParameterFetcher
Note: Retrieves the files from a .zip file and expose those as features.
ParameterFetcher
    ATTR_LIST = sourceZipFile {$(sourceZipFile)}
    -> readZipContentPy
readZipContentPy: PythonCaller
    NEW_ATTRIBUTES = _zipFileContent{}
    PYTHONSOURCE:
      import fmeobjects
      # Template Function interface:
      def processFeature(feature):
          pass

      # Template Class Interface:
      class FeatureProcessor(object):
          def __init__(self):
              pass
          def input(self,feature):
              import zipfile
              # get file name form FME
              myzipfile = feature.getAttribute("sourceZipFile")
              # zipfileContent list that we will send back to FME
              _zipFileContent=[]
              # Open zip file.
              try:
                  zz = zipfile.ZipFile(myzipfile)

                  #zz.printdir()
                  for name in zz.infolist():
                      _zipFileContent.append(name.filename)
                  zz.close()
              except:
                  pass
              # send content back to FME as a list
              feature.setAttribute("_zipFileContent{}",_zipFileContent)
              self.pyoutput(feature)
          def close(self):
              pass
    PYTHONSYMBOL = FeatureProcessor
    -> ListExploder
ListExploder
    ATTR_ACCUM_MODE = Merge List Attributes
    ATTR_CONFLICT_RES = Use List Attribute Values
    INDEX_ATTR = fileCounter
    LIST_ATTR = _zipFileContent{}
    ELEMENTS -> AttributeRenamer
AttributeRenamer
    ATTR_TABLE = RENAME_SET_DEFAULT _zipFileContent > zipFileName
    -> FilenamePartExtractor
FilenamePartExtractor
    EXTENSION_ATTR = fileExtension
    SRC_ATTR = @Value(zipFileName)
    -> Files (output)
Files (output)

FME custom transformer FileSystemDeleteMoveCopyExist_4
This is python a based Transformer that can "move","copy","delete" and can check if a file "exist". The script is fairly simple. You have three fields.
action:"move","copy","delete","exist" 
fileInput: provide the input file path.
fileOutput: provide the output file path. (Is not used when you delete or test the existance of a file)

Parameters:
- ACTION =
- FILEINPUT =
- FILEOUTPUT =

FileName (input)
    -> PythonCaller
PythonCaller
    NEW_ATTRIBUTES = "_status "
    PYTHONSOURCE:
      import fmeobjects
      # Template Function interface:
      def processFeature(feature):
          pass

      # Template Class Interface:
      class FeatureProcessor(object):
          def __init__(self):
              pass
          def input(self,feature):
              import os,shutil

              # define and get parameters
              self._status=''
              self._fileInput = feature.getAttribute('fileInput')
              self._fileOutput = feature.getAttribute('fileOutput')
              self._action = feature.getAttribute('action')

              # When action is "delete"
              if (self._action.upper() == "DELETE"):
                  if os.path.exists(self._fileInput):
                      os.remove(self._fileInput)
                      self._status='deleted'
                  else:
                      self._status='notexist:' + self._fileInput

              # When action is "copy"
              if (self._action.upper() == "COPY"):
                  if os.path.exists(self._fileInput):
                      shutil.copy(self._fileInput,self._fileOutput)
                      self._status='copied'
                  else:
                      self._status='notexist:' + self._fileInput

              # When action is "move"
              if (self._action.upper() == "MOVE"):
                  if os.path.exists(self._fileInput):
                      shutil.move(self._fileInput,self._fileOutput)
                      self._status='moved'
                  else:
                      self._status='notexist:' + self._fileInput

              # When action is " mkdir"
              if (self._action.upper() == "MKDIR"):
                  if os.path.exists(self._fileInput):
                      self._status='created'
                  else:
                      os.mkdir(self._fileInput)
                      self._status='created'

              # When action is " rmdir"
              if (self._action.upper() == "RMDIR"):
                  if os.path.exists(self._fileInput):
                      self._status='created'
                  else:
                      os.rmdir(self._fileInput)
                      self._status='created'

              # When action is "exist"
              if (self._action.upper() == "EXIST"):
                  if os.path.exists(self._fileInput):
                      self._status='exist'
                  else:
                      self._status='notexist:' + self._fileInput

              feature.setAttribute('_status',self._status)
              self.pyoutput(feature)
          def close(self):
              pass
    PYTHONSYMBOL = FeatureProcessor
    -> TestFilter
TestFilter
    DEFAULT_VALUE = Failed
    TEST_LIST:
      BOOL_OP,OR,COMPOSITE_TEST,<Unused>,TEST_CLAUSE,"TEST @Value(_status) = deleted
      TEST @Value(_status) = copied
      TEST @Value(_status) = moved
      TEST @Value(_status) = exist
      TEST @Value(_status) = created",Success
    Success -> Success (output)
    Failed -> Failed (output)
Success (output)
Failed (output)

FME custom transformer FileSystemDeleteMoveCopyExist
This transformer can "move","copy","delete" files. Can as well check if a file "exist" and create or delete folders.
action:The action you like to perform. 
    fileInput: provide the input file path.
    fileOutput: provide the output file path. (Is not used when you delete or test the existance of a file)

Parameters:
- Action =
- FILEINPUT =
- FILEOUTPUT =

FileName (input)
    -> ParameterFetcher
ParameterFetcher
    ATTR_LIST = action {$(Action)} fileInput {$(FILEINPUT)} fileOutput {$(FILEOUTPUT)}
    -> PythonCaller
PythonCaller
    NEW_ATTRIBUTES = "_status "
    PYTHONSOURCE:
      import fmeobjects
      # Template Function interface:
      def processFeature(feature):
          pass

      # Template Class Interface:
      class FeatureProcessor(object):
          def __init__(self):
              pass
          def input(self,feature):
              import os,shutil

              # define and get parameters
              self._status=''
              self._fileInput = feature.getAttribute('fileInput')
              self._fileOutput = feature.getAttribute('fileOutput')
              self._action = feature.getAttribute('action')

              # When action is "delete"
              if (self._action.upper() == "DELETE"):
                  if os.path.exists(self._fileInput):
                      os.remove(self._fileInput)
                      self._status='deleted'
                  else:
                      self._status='notexist:' + self._fileInput

              # When action is "delete folder"
              if (self._action.upper() == "RMDIR"):
                  if os.path.exists(self._fileInput):
                      shutil.rmtree(self._fileInput)
                      self._status='deleted'
                  else:
                      self._status='notexist:' + self._fileInput

              # When action is "copy"
              if (self._action.upper() == "COPY"):
                  if os.path.exists(self._fileInput):
                      shutil.copy(self._fileInput,self._fileOutput)
                      self._status='copied'
                  else:
                      self._status='notexist:' + self._fileInput

              # When action is "move"
              if (self._action.upper() == "MOVE"):
                  if os.path.exists(self._fileInput):
                      shutil.move(self._fileInput,self._fileOutput)
                      self._status='moved'
                  else:
                      self._status='notexist:' + self._fileInput

              # When action is " mkdir"
              if (self._action.upper() == "MKDIR"):
                  if os.path.exists(self._fileInput):
                      self._status='created'
                  else:
                      os.makedirs(self._fileInput)
                      self._status='created'

              # When action is "exist"
              if (self._action.upper() == "EXIST"):
                  if os.path.exists(self._fileInput):
                      self._status='exist'
                  else:
                      self._status='notexist:' + self._fileInput

              feature.setAttribute('_status',self._status)
              self.pyoutput(feature)
          def close(self):
              pass
    PYTHONSYMBOL = FeatureProcessor
    -> TestFilter
TestFilter
    DEFAULT_VALUE = Failed
    TEST_LIST:
      BOOL_OP,OR,COMPOSITE_TEST,<Unused>,TEST_CLAUSE,"TEST @Value(_status) = deleted
      TEST @Value(_status) = copied
      TEST @Value(_status) = moved
      TEST @Value(_status) = exist
      TEST @Value(_status) = created",Success,BOOL_OP,OR,COMPOSITE_TEST,<Unused>,TEST_CLAUSE,"TEST @Value(_status) BEGINS_WITH notexist:",DoesNotExist
    Success -> Success (output)
    DoesNotExist -> NotFound (output)
    Failed -> Failed (output)
Success (output)
NotFound (output)
Failed (output)

FME custom transformer CleanUpBlob

Parameters:
- AZUREDIMENSIONFILE =
- FILEID =
- NAME =

Input (input)
    -> TestFilter
    -> FeatureHolder
TestFilter
    DEFAULT_VALUE = NoFileInAzure
    TEST_LIST = BOOL_OP,OR,COMPOSITE_TEST,<Unused>,TEST_CLAUSE,"TEST @Value(AzureDimensionFile) ATTRIBUTE_HAS_VALUE """"",DimFileExistsInAzure
    DimFileExistsInAzure -> AzureBlobLister
Note: Can we not be more specific! I need to read the entire container
AzureBlobLister
    ACCOUNT = cwsblobstorage01
    CONTAINER = cwsblob01
    DELIMITER = /
    KEY =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
    PREFIX = @Value(AzureDimensionFile)
    RECURSIVE = Yes
    Blob -> FeatureHolder_2
FeatureHolder_2
    -> AzureBlobDeleter
AzureBlobDeleter
    ACCOUNT = cwsblobstorage01
    BLOB_NAME = @Value(Blob.Name)
    CONTAINER = cwsblob01
    KEY =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
    Deleted -> AttributeKeeper
    Fail -> AttributeKeeper
Note: Remove all attributes
AttributeKeeper
    CREATE_BULK_MODE_FEATURES = No
    -> FeatureHolder
FeatureHolder
    -> TestFilter_2
TestFilter_2
    DEFAULT_VALUE = <UNFILTERED>
    TEST_LIST = BOOL_OP,OR,COMPOSITE_TEST,<Unused>,TEST_CLAUSE,"TEST @Value(FileId) ATTRIBUTE_HAS_VALUE """"",FileId ATTRIBUTE_HAS_VALUE
    FileId ATTRIBUTE_HAS_VALUE -> Initiator (output)
Initiator (output)

FME custom transformer FileSystemDeleteMoveCopyExist_3
This transformer can "move","copy","delete" files. Can as well check if a file "exist" and create or delete folders.
action:The action you like to perform. 
    fileInput: provide the input file path.
    fileOutput: provide the output file path. (Is not used when you delete or test the existance of a file)

Parameters:
- Action =
- FILEINPUT =
- FILEOUTPUT =

FileName (input)
    -> ParameterFetcher
ParameterFetcher
    ATTR_LIST = action {$(Action)} fileInput {$(FILEINPUT)} fileOutput {$(FILEOUTPUT)}
    -> PythonCaller
PythonCaller
    NEW_ATTRIBUTES = "_status "
    PYTHONSOURCE:
      import fmeobjects
      # Template Function interface:
      def processFeature(feature):
          pass

      # Template Class Interface:
      class FeatureProcessor(object):
          def __init__(self):
              pass
          def input(self,feature):
              import os,shutil

              # define and get parameters
              self._status=''
              self._fileInput = feature.getAttribute('fileInput')
              self._fileOutput = feature.getAttribute('fileOutput')
              self._action = feature.getAttribute('action')

              # When action is "delete"
              if (self._action.upper() == "DELETE"):
                  if os.path.exists(self._fileInput):
                      os.remove(self._fileInput)
                      self._status='deleted'
                  else:
                      self._status='notexist:' + self._fileInput

              # When action is "delete folder"
              if (self._action.upper() == "RMDIR"):
                  if os.path.exists(self._fileInput):
                      shutil.rmtree(self._fileInput)
                      self._status='deleted'
                  else:
                      self._status='notexist:' + self._fileInput

              # When action is "copy"
              if (self._action.upper() == "COPY"):
                  if os.path.exists(self._fileInput):
                      shutil.copy(self._fileInput,self._fileOutput)
                      self._status='copied'
                  else:
                      self._status='notexist:' + self._fileInput

              # When action is "move"
              if (self._action.upper() == "MOVE"):
                  if os.path.exists(self._fileInput):
                      shutil.move(self._fileInput,self._fileOutput)
                      self._status='moved'
                  else:
                      self._status='notexist:' + self._fileInput

              # When action is " mkdir"
              if (self._action.upper() == "MKDIR"):
                  if os.path.exists(self._fileInput):
                      self._status='created'
                  else:
                      os.makedirs(self._fileInput)
                      self._status='created'

              # When action is "exist"
              if (self._action.upper() == "EXIST"):
                  if os.path.exists(self._fileInput):
                      self._status='exist'
                  else:
                      self._status='notexist:' + self._fileInput

              feature.setAttribute('_status',self._status)
              self.pyoutput(feature)
          def close(self):
              pass
    PYTHONSYMBOL = FeatureProcessor
    -> TestFilter
TestFilter
    DEFAULT_VALUE = Failed
    TEST_LIST:
      BOOL_OP,OR,COMPOSITE_TEST,<Unused>,TEST_CLAUSE,"TEST @Value(_status) = deleted
      TEST @Value(_status) = copied
      TEST @Value(_status) = moved
      TEST @Value(_status) = exist
      TEST @Value(_status) = created",Success,BOOL_OP,OR,COMPOSITE_TEST,<Unused>,TEST_CLAUSE,"TEST @Value(_status) BEGINS_WITH notexist:",DoesNotExist
    Success -> Success (output)
    DoesNotExist -> NotFound (output)
    Failed -> Failed (output)
Success (output)
NotFound (output)
Failed (output)

FME custom transformer FileSystemDeleteMoveCopyExist_2
This is python a based Transformer that can "move","copy","delete" and can check if a file "exist". The script is fairly simple. You have three fields.
action:"move","copy","delete","exist" 
fileInput: provide the input file path.
fileOutput: provide the output file path. (Is not used when you delete or test the existance of a file)

Parameters:
- ACTION =
- FILEINPUT =
- FILEOUTPUT =

FileName (input)
    -> PythonCaller
PythonCaller
    NEW_ATTRIBUTES = "_status "
    PYTHONSOURCE:
      import fmeobjects
      # Template Function interface:
      def processFeature(feature):
          pass

      # Template Class Interface:
      class FeatureProcessor(object):
          def __init__(self):
              pass
          def input(self,feature):
              import os,shutil

              # define and get parameters
              self._status=''
              self._fileInput = feature.getAttribute('fileInput')
              self._fileOutput = feature.getAttribute('fileOutput')
              self._action = feature.getAttribute('action')

              # When action is "delete"
              if (self._action.upper() == "DELETE"):
                  if os.path.exists(self._fileInput):
                      os.remove(self._fileInput)
                      self._status='deleted'
                  else:
                      self._status='notexist:' + self._fileInput

              # When action is "copy"
              if (self._action.upper() == "COPY"):
                  if os.path.exists(self._fileInput):
                      shutil.copy(self._fileInput,self._fileOutput)
                      self._status='copied'
                  else:
                      self._status='notexist:' + self._fileInput

              # When action is "move"
              if (self._action.upper() == "MOVE"):
                  if os.path.exists(self._fileInput):
                      shutil.move(self._fileInput,self._fileOutput)
                      self._status='moved'
                  else:
                      self._status='notexist:' + self._fileInput

              # When action is " mkdir"
              if (self._action.upper() == "MKDIR"):
                  if os.path.exists(self._fileInput):
                      self._status='created'
                  else:
                      os.mkdir(self._fileInput)
                      self._status='created'

              # When action is " rmdir"
              if (self._action.upper() == "RMDIR"):
                  if os.path.exists(self._fileInput):
                      self._status='created'
                  else:
                      os.rmdir(self._fileInput)
                      self._status='created'

              # When action is "exist"
              if (self._action.upper() == "EXIST"):
                  if os.path.exists(self._fileInput):
                      self._status='exist'
                  else:
                      self._status='notexist:' + self._fileInput

              feature.setAttribute('_status',self._status)
              self.pyoutput(feature)
          def close(self):
              pass
    PYTHONSYMBOL = FeatureProcessor
    -> TestFilter
TestFilter
    DEFAULT_VALUE = Failed
    TEST_LIST:
      BOOL_OP,OR,COMPOSITE_TEST,<Unused>,TEST_CLAUSE,"TEST @Value(_status) = deleted
      TEST @Value(_status) = copied
      TEST @Value(_status) = moved
      TEST @Value(_status) = exist
      TEST @Value(_status) = created",Success
    Success -> Success (output)
    Failed -> Failed (output)
Success (output)
Failed (output)

FME custom transformer ValidateZipContent

Parameters:
- FILEID =
- SOURCEFILE =

Input (input)
    -> AttributeCreator_4
AttributeCreator_3
    ATTR_TABLE:
      SET_TO fme_feature_type = @Value(SourceFile)\@Value(zipFileName)
      SET_TO file_type = shp
    -> Continue (output)
    -> FeatureReaderSHP [INITIATOR]
FeatureReaderSHP
    ATTR_ACCUM_MODE = Only Use Result
    COMBINE_GEOM = Use Result
    DATASET = @Value(fme_feature_type)
    ESRISHAPE_SIMPLE_DONUT_GEOMETRY = simple
    ESRISHAPE_UPPER_CASE_ATTR_NAMES = No
    ESRISHAPE_USE_SEARCH_ENVELOPE = NO
    FORMAT = ESRISHAPE
    INTERACT = <No Spatial Filter>
    OUTPUT_FEATURES_DISPLAY = Schema Features
    <SCHEMA> -> AttributeRemover
AttributeCreator_5
    ATTR_TABLE:
      SET_TO fme_feature_type = @Value(SourceFile)\@Value(zipFileName)
      SET_TO file_type = gdb
    -> Continue (output)
    -> FeatureReaderGDB [INITIATOR]
FeatureReaderGDB
    ATTR_ACCUM_MODE = Only Use Result
    COMBINE_GEOM = Use Result
    DATASET = @Value(fme_feature_type)
    FORMAT = GEODATABASE_FILE
    GEODATABASE_FILE_ALIAS_MODE = NONE
    GEODATABASE_FILE_CACHE_MULTIPATCH_TEXTURES = yes
    GEODATABASE_FILE_CHECK_SIMPLE_GEOM = no
    GEODATABASE_FILE_CREATE_FEATURE_TABLES_FROM_DATA = Yes
    GEODATABASE_FILE_FEATURE_READ_MODE = Features
    GEODATABASE_FILE_IGNORE_NETWORK_INFO = yes
    GEODATABASE_FILE_IGNORE_RELATIONSHIP_INFO = yes
    GEODATABASE_FILE_MERGE_FEAT_LINKED_ANNOS = no
    GEODATABASE_FILE_QUERY_FEATURE_TYPES_FOR_MERGE_FILTERS = Yes
    GEODATABASE_FILE_RESOLVE_DOMAINS = no
    GEODATABASE_FILE_RESOLVE_SUBTYPE_NAMES = yes
    GEODATABASE_FILE_SPLIT_COMPLEX_ANNOS = no
    GEODATABASE_FILE_SPLIT_COMPLEX_EDGES = no
    GEODATABASE_FILE_SPLIT_MULTI_PART_ANNOS = no
    GEODATABASE_FILE_STRIP_GUID_GLOBALID_BRACES = no
    GEODATABASE_FILE_TRANSLATE_SPATIAL_DATA_ONLY = no
    GEODATABASE_FILE_USE_SEARCH_ENVELOPE = NO
    INTERACT = <No Spatial Filter>
    OUTPUT_FEATURES_DISPLAY = Schema Features
    <SCHEMA> -> AttributeRemover
AttributeCreator_6
    ATTR_TABLE:
      SET_TO fme_feature_type = @Value(SourceFile)\@Value(zipFileName)
      SET_TO file_type = gpkg
    -> Continue (output)
    -> FeatureReaderGPKG [INITIATOR]
Continue (output)
FeatureReaderGPKG
    ATTR_ACCUM_MODE = Only Use Result
    COMBINE_GEOM = Use Result
    DATASET = @Value(fme_feature_type)
    FORMAT = OGCGEOPACKAGE
    INTERACT = <No Spatial Filter>
    OGCGEOPACKAGE_ENCODE_FEATURE_TYPE_AND_ATTR_NAMES = YES
    OGCGEOPACKAGE_ENFORCE_FOREIGN_KEY_INTEGRITY = YES
    OGCGEOPACKAGE_OPEN_SINGLE_RASTER_AS_SUBDATASET = YES
    OGCGEOPACKAGE_QUERY_FEATURE_TYPES_FOR_MERGE_FILTERS = Yes
    OGCGEOPACKAGE_READ_BOOLEANS_AS_YES_NO = YES
    OGCGEOPACKAGE_READ_NULLS = YES
    OGCGEOPACKAGE_USE_SEARCH_ENVELOPE = NO
    OUTPUT_FEATURES_DISPLAY = Schema Features
    <SCHEMA> -> AttributeRemover
AttributeRemover
    REMOVE_ATTRS = _scanZipInZip,FMEJobIdValidator,fme_format_short_name,path_windows,_inputZipFile,SourceFile_extension,fileCounter,fme_format_long_name,fileExtension,fme_feature_type_name,sourceZipFile,zipFileName,SourceFile
    -> ListExploder
ListExploder
    ATTR_ACCUM_MODE = Merge List Attributes
    ATTR_CONFLICT_RES = Use List Attribute Values
    INDEX_ATTR = _element_index
    LIST_ATTR = attribute{}
    ELEMENTS -> Category_fileOrder
    ELEMENTS -> Sampler
Category_fileOrder: Counter
    CNT_ATTR = _count
    DOMAIN = counter
    SCOPE = Local
    START = 3
    -> Category
Category: AttributeCreator
    ATTR_TABLE = SET_TO FieldOrder = @Evaluate(@Value(_count)+1)
    -> ConvertFMEDataTypesToMSSQLTypes_2
ConvertFMEDataTypesToMSSQLTypes_2
    FIELDTYPE = @Value(fme_data_type)
    NAME = @Value(name)
    -> Attr_Fields
Attr_Fields: AttributeCreator
    ATTR_TABLE:
      SET_TO FileId = @Value(FileId)
      SET_TO FieldName = @Value(FieldName)
      SET_TO FieldType = @Value(FieldType)
      SET_TO Alias = @Value(FieldName)
      SET_TO Title
      SET_TO Description
      SET_TO IgnoreField = 0
    -> Fields (output)
Fields (output)
StringReplacer
    CASE = NO
    FIND_TEXT = '
    NO_MATCH = _FME_NO_OP_
    REGEXP = NO
    REPLACE_TEXT = ''
    SRC_ATTRS = ErrorMessage
    -> Error (output)
Error (output)

Bookmark: Get JobId
AttributeCreator_4
    ATTR_TABLE = SET_TO FMEJobIdValidator = FME_CONDITIONAL:DEFAULT_VALUE'-1'BOOL_OP;OR;COMPOSITE_TEST;<Unused>;TEST $(FME_JOB_ID) ATTRIBUTE_HAS_VALUE _FME_BLANK_STRING_'$(FME_JOB_ID)'FME_NUM_CONDITIONS2___
    -> FilenamePartExtractor

Bookmark: Check File extension
FilenamePartExtractor
    EXTENSION_ATTR = SourceFile_extension
    SRC_ATTR = @Value(SourceFile)
    -> TestFilter
TestFilter
    DEFAULT_VALUE = OtherFormat
    TEST_LIST = BOOL_OP,OR,COMPOSITE_TEST,<Unused>,TEST_CLAUSE,"TEST @LowerCase(@Value(SourceFile_extension)) = zip",IsAZipFile
    IsAZipFile -> getMetaDataFromZip [InputZip]
    OtherFormat -> AttributeCreator
AttributeCreator
    ATTR_TABLE = SET_TO ErrorMessage = File must be a .zip that contains a shape file and it related files (.shp,.dbf,.prj,.sbn,.sbx,.shx).
    -> StringReplacer

Bookmark: Read zip and find .tiff and .legend
getMetaDataFromZip
    inputZipFile = @Value(SourceFile)
    scanZipInZip = yes
    -> TestFilter_2
    -> Aggregator

Bookmark: Check if .shp exists
TestFilter_2
    DEFAULT_VALUE = File is missing
    TEST_LIST = "BOOL_OP,OR,COMPOSITE_TEST,""""""1"""""",TEST_CLAUSE,TEST @LowerCase(@Value(fileExtension)) CONTAINS shp",shp,"BOOL_OP,OR,COMPOSITE_TEST,""""""1"""""",TEST_CLAUSE,TEST @LowerCase(@Value(fileExtension)) CONTAINS gdb",gdb,"BOOL_OP,OR,COMPOSITE_TEST,""""""1"""""",TEST_CLAUSE,TEST @LowerCase(@Value(fileExtension)) CONTAINS gpkg",gpkg
    shp -> AttributeCreator_3
    gdb -> AttributeCreator_5
    gpkg -> AttributeCreator_6
Aggregator
    ACCUM_ATTRS_NAME = Use Attributes From One Feature
    AGGREGATE_TYPE = Homogeneous Collection (If Possible)
    CONCAT_ATTRS = fileExtension
    MODE = Geometry - Assemble One Level
    ORDERED = No
    SEP = ,
    AGGREGATE -> TestFilter_3
TestFilter_3
    DEFAULT_VALUE = DidNotFindValidExtension
    TEST_LIST:
      "BOOL_OP,OR,COMPOSITE_TEST,""""""1 OR 2 OR 3"""""",TEST_CLAUSE,TEST shp IN @Value(fileExtension)
      TEST gdb IN @Value(fileExtension)
      TEST gpkg IN @Value(fileExtension)",FoundValidExtension
    DidNotFindValidExtension -> AttributeCreator_2
AttributeCreator_2
    ATTR_TABLE = SET_TO ErrorMessage = .SHP-file, .GDB-file or .GPKG-file could not be found.
    -> StringReplacer

Bookmark: Create fields for Grid data
Sampler
    RATE = 1
    SAMPLE_MODE = No
    SAMPLE_TYPE_LONG = First N Features
    SAMPLED -> add_GridNum
    SAMPLED -> add_x
    SAMPLED -> add_y
add_GridNum: AttributeCreator
    ATTR_TABLE:
      SET_TO FieldName = GridNum
      SET_TO FieldType = bigint
      SET_TO Alias = GridNum
      SET_TO Title = Grid Coding system
      SET_TO Description = Unique coding system that maps all grid cells together
      SET_TO IgnoreField = 1
      SET_TO FieldOrder = 3
    -> Fields (output)
add_x: AttributeCreator
    ATTR_TABLE:
      SET_TO FieldName = x
      SET_TO FieldType = int
      SET_TO Alias = x
      SET_TO Title = x-coordinate
      SET_TO Description = Point cloud must export x-coordinate
      SET_TO IgnoreField = 1
      SET_TO FieldOrder = 1
    -> Fields (output)
add_y: AttributeCreator
    ATTR_TABLE:
      SET_TO FieldName = y
      SET_TO FieldType = int
      SET_TO Alias = y
      SET_TO Title = y-coordinate
      SET_TO Description = Point cloud must have y-coordinate exported
      SET_TO IgnoreField = 1
      SET_TO FieldOrder = 2
    -> Fields (output)

FME custom transformer ZipArchiver
Compresses a file or folder and appends it into the specified zip file.
    The archive name will be the same as the target file name. If a file having the same name as the target file has been archived in the zip file already, the file will not be archived.
    The transformer creates a new zip file when receiving the first file that should be archived into it, if the specified zip file doesn't exist. 
    -----
    Note: This transformer has been basically internationalized with 2016-01-22 update. However, depending on the environment (platform, OS version etc.), file path strings containing Non-ASCII characters still may not be treated correctly. Please test enough if the path strings may contain Non-ASCII characters.
    -----
    Input features will be output through the Output port as-is.
    The transformer creates log features which contain these attributes for each file, and outputs them from the LogSuccess/LogFailure port.
    - Result: "success" if the file was archived successfully, "failure" otherwise.
    - Target File: the target file path.
    - Zip File: the zip file path.
    - Archive Name: the archive name of the target file in the zip file if archived successfully, empty otherwise.
    - Comment: compression ratio if archived successfully, failure reason otherwise.
    ファイルまたはフォルダを圧縮し、指定したzipファイルに追加します。
    アーカイブ名は対象のファイル名と同じになります。対象とするファイルと同じ名前のファイルがすでにzipファイルにアーカイブされていた場合、そのファイルはアーカイブされません。
    指定したzipファイルが存在しない場合、このトランスフォーマーはそれにアーカイブすべき最初のファイルを受け取ったときに新しいzipファイルを作成します。
-----
    注: 2016-01-22 の更新によって、このトランスフォーマーは基本的には国際化されました。しかし、環境（プラットフォームやOSのバージョンなど）によっては、ASCII文字（半角の英数字や記号）以外の文字を含むファイルパス文字列ま、まだ正しく処理されない可能性があります。パス文字列に非ASCII文字が含まれる可能性がある場合は、十分にテストしてください。
-----
    入力フィーチャーはそのままOutputポートから出力されます。
    このトランスフォーマーは、次の属性を持つログフィーチャーをファイルごとに作成し、LogSuccess/LogFailureポートから出力します。
    - Result: ファイルが正常にアーカイブされた場合は"succcess"、そうでない場合は"failure"
    - Target File: 対象のファイルパス
    - Zip File: zipファイルパス
    - Archive Name: アーカイブに成功した場合はzipファイル内でのアーカイブ名、失敗した場合は空文字列
    - Comment: アーカイブに成功した場合は圧縮率、失敗した場合はその理由
Parameters 
    Target File or Folder
    : 
    Specify a file or folder path that should be archived. You can also set a feature attribute value to this parameter.
    If you specify a folder path here, all files under the folder will be archived. In the case, the original directory structure will also be preserved, and the archive name of the file will contain path starting from the specified folder.
    アーカイブするファイルまたはフォルダのパスを指定します。フィーチャーの属性をこのパラメーターに設定することもできます。 
    ここにフォルダのパスを指定した場合は、そのフォルダ以下にある全てのファイルがアーカイブされます。その場合、元のディレクトリ構造も維持され、ファイルのアーカイブ名には、指定されたフォルダから始まるパスが含まれます。
    Destination Zip File
    : 
    Specify a zip file path (*.zip). You can also set a feature attribute value to this parameter.
    If the extension of the specified file path is not "zip", the transformer will add ".zip" to the path automatically. 
    zipファイルパス（*.zip）を指定します。フィーチャーの属性をこのパラメーターに設定することもできます。 
    指定されたパスの拡張子が"zip"でない場合は、そのパスに".zip"を自動的に付加します。
    If Destination Zip File Exists
    :
    If the specified destination zip file exists at the translation starting time, this transformer appends compressed files into the existing zip file, by default. If you set 
    "Remove Existing Zip File"
    to this parameter, this transformer removes the existing zip file once at first, and then appends compressed files into the newly created same name zip file. If you set 
    "Rename Destination Zip File"
    , an suffix will be added to the destination zip file name automatically to differentiate from the existing zip file.
    変換の開始時に指定されたzipファイルが存在する場合、デフォルトでは、このトランスフォーマーは既存のzipファイルに圧縮したファイルを追加します。このパラメーターに 
    "Remove Existing Zip File"
    を設定した場合は、このトランスフォーマーは最初に一回だけ既存のzipファイルを削除してから、新たに作成した同じ名前のzipファイルに圧縮したファイルを追加します。
    "Rename Destination Zip File"
    を設定した場合は、既存のzipファイルと区別するため、出力先のzipファイル名にサフィクスが自動的に付加されます。
    Compression Level (Python 3.7+)
    :
    If FME uses Python 3.7+ when running the workspace, you can control the compression levels with this parameter.
        Level 0 indicates just archiving with no compression.
        In a level between 1-9, less number indicates faster and less compression, greater number indicates slower and more compression. However, the order of the numbers does not always exactly match the order of actual compression levels. Depending on the conditions, 6 could be more compression than 9 for example.
        Currently (in Python 3.7), "Default" is equivalent to level 6, but it may be changed in the future.
    This parameter works only with Python 3.7 or later. If the version of Python interpreter is 3.6 or earlier, this parameter setting will just be ignored. 
    FMEがワークスペースの実行時にPython 3.7以降を使用する場合、このパラメーターによって圧縮レベルを指定できます。
        レベル0は、圧縮せずに単にアーカイブすることを示します。
        1から9の間のレベルは、数値が小さいほど高速で圧縮率が低く、数値が大きいほど低速で圧縮率が高いことを示します。ただし、この順番は必ずしも実際の圧縮率の順番と一致するとは限りません。例えば、条件によっては6が9よりも高い圧縮率となることもあります。
        現在（Python 3.7）は"Default"はレベル6と等価ですが、将来変更されるかもしれません。
    このパラメーターはPython 3.7以降でのみ機能します。 Pythonインタープリターのバージョンが3.6以前の場合、このパラメーター設定は無視されます。

Parameters:
- COMPRESSION_LEVEL =
- FILE_PATH =
- MODE =
- ZIP_PATH =

Input (input)
    -> ParameterFetcher
ParameterFetcher
    ATTR_LIST = __ziparchiver.filepath $(FILE_PATH) __ziparchiver.zippath $(ZIP_PATH) __ziparchiver.mode $(MODE) __ziparchiver.compression_level $(COMPRESSION_LEVEL)
    -> PythonCaller
PythonCaller
    NEW_ATTRIBUTES = __ziparchiver.result
    PYTHONSOURCE:
      # 2015-05-24, Takashi Iijima, Original Implementation
      # 2016-01-22, Takashi Iijima, Refactoring and Internationalizing (Tech Preview)
      # 2018-05-02, Takashi Iijima, Avoided 'divided by 0' error that occurred if the original file size was zero.
      # 2018-07-12, Takashi Iijima, Allow Zip64 by default. Thanks to David R.
      # 2020-01-13, Takashi Iijima, Changed Default Python Interpreter to 3.6+, saved with FME 2017.1.2.1
      # 2020-04-25, Takashi Iijima, Added Compression Level option parameter.

      import fme
      import fmeobjects
      import os, zipfile

      class ZipArchiver(object):
          def __init__(self):
              import platform
              majorVersion = int(platform.python_version_tuple()[0])
              if majorVersion < 3:
                  import locale
                  t = locale.getdefaultlocale()
                  self.encode = lambda s: (s.encode(t[1]) if t else s) if isinstance(s, unicode) else s
              else:
                  self.encode = lambda s: s
              self.logger = fmeobjects.FMELogFile()
              self.zpaths = {} # key: specified zip file path (lower-case), value: treated zip file path in this session

          def input(self, feature):
              try:
                  # Retrieve target file path and zip file path from feature attributes.
                  # If the specified zip file path doesn't end with ".zip", add the extension.
                  regulatePath = lambda path: os.path.abspath(path).replace('\\', '/')
                  fpath = regulatePath(feature.getAttribute('__ziparchiver.filepath'))
                  zpath = regulatePath(feature.getAttribute('__ziparchiver.zippath'))
                  if not zpath.lower().endswith('.zip'):
                      zpath = '%s.zip' % zpath
                  keyPath = zpath.lower()

                  mode = feature.getAttribute('__ziparchiver.mode')
                  if os.path.exists(zpath):
                      if mode == 'REMOVE':
                          if keyPath not in self.zpaths:
                              os.remove(zpath)
                      elif mode == 'RENAME':
                          if keyPath in self.zpaths:
                              zpath = self.zpaths[keyPath]
                          else:
                              format, n = '%s_%d.zip', 1
                              while os.path.exists(format % (zpath[:-4], n)): n += 1
                              zpath = format % (zpath[:-4], n)
                  self.zpaths[keyPath] = zpath

                  # Collect target file paths, including empty directries if "fpath" is a directory.
                  # If specified file/directory doesn't exist, throw an error.
                  root = ''
                  fpaths, dpaths = [], []
                  if os.path.exists(fpath): # fpath is a file
                      root = os.path.split(fpath)[0]
                      if os.path.isfile(fpath):
                          fpaths = [fpath]
                      elif os.listdir(fpath): # fpath is a non-empty directory
                          for dirpath, dirnames, filenames in os.walk(fpath):
                              paths = [os.path.join(dirpath, d) for d in dirnames]
                              dpaths += [regulatePath(path) for path in paths if not os.listdir(path)]
                              fpaths += [regulatePath(os.path.join(dirpath, f)) for f in filenames]
                      else: # fpath is an empty directory
                          dpaths = [fpath]
                  else:
                      raise Exception('specified file doesn\'t exist.')

                  # If destination directory doesn't exist, create the directory.
                  if not os.path.exists(os.path.split(zpath)[0]):
                      os.makedirs(os.path.split(zpath)[0])

                  # Then, perform archiving.
                  # Add "compresslevel" parameter if 3.7 <= Version of Python interpreter.
                  expression = "zipfile.ZipFile(zpath, 'a', zipfile.ZIP_DEFLATED, allowZip64=True"
                  import platform
                  vmajor, vminor, _ = platform.python_version_tuple()
                  if 3 <= int(vmajor) and 7 <= int(vminor):
                      level = feature.getAttribute('__ziparchiver.compression_level')
                      expression = expression + ', compresslevel=%s' % level
                  with eval(expression + ')') as zipper:
                      for path in [path for path in fpaths if path.lower() != zpath.lower()]:
                          aname = path[len(root) + 1:] # archive name
                          result, msg = False, ''
                          try:
                              info = zipper.getinfo(aname)
                              msg = '"%s" exists in the archive already.' % aname
                          except:
                              try:
                                  zipper.write(path, aname)
                                  info = zipper.getinfo(aname)
                                  after = info.compress_size/1024.0
                                  before = info.file_size/1024.0
                                  rate = ('%.1f%%' % (after/before*100.0)) if 0 < before else 'N/A'
                                  msg = '%s (%.1f / %.1f KB)' % (rate, after, before)
                                  result = True
                              except Exception as ex:
                                  msg = '%s' % ex
                          self.outputLogFeature('Success' if result else 'Failure', path, zpath, aname, msg)
                      for path in dpaths:
                          aname = path[len(root) + 1:] # archive name
                          try:
                              info = zipper.getinfo(aname)
                          except:
                              zipper.write(path, aname)
              except Exception as ex:
                  self.outputLogFeature('Terminate', fpath, zpath, '', '%s' % ex)
              finally: # always output the input feature through the Output port.
                  self.pyoutput(feature)

          # Output a log feature.
          def outputLogFeature(self, flag, fpath, zpath, aname, msg):
              if flag != 'Success':
                  self.logger.logMessageString(self.encode('ZipArchiver: %s' % msg), \
                      fmeobjects.FME_ERROR if flag == 'Terminate' else fmeobjects.FME_WARN)
              feature = fmeobjects.FMEFeature()
              feature.setAttribute('__ziparchiver.result', flag.lower())
              feature.setAttribute('Target File', fpath)
              feature.setAttribute('Zip File', zpath)
              feature.setAttribute('Archive Name', aname if flag == 'Success' else '')
              feature.setAttribute('Comment', msg)
              feature.setAttribute('fme_feature_type', 'ZipArchiver_%s' % flag)
              self.pyoutput(feature)
    PYTHONSYMBOL = ZipArchiver
    -> Tester
Tester
    BOOL_OP = OR
    TEST_CLAUSE = TEST __ziparchiver.result ATTRIBUTE_IS_MISSING ""
    TEST_MODE = Automatic
    PASSED -> Output (output)
    FAILED -> AttributeRenamer
Output (output)
AttributeRenamer
    ATTR_LIST = __ziparchiver.result,Result,
    -> AttributeExposer
AttributeExposer
    ATTR_LIST = "Target File","Zip File","Archive Name",Comment
    -> AttributeKeeper
AttributeKeeper
    CREATE_BULK_MODE_FEATURES = No
    KEEP_ATTRS = Archive Name,Comment,Result,Target File,Zip File
    -> AttributeFilter
AttributeFilter
    ATTR_NAME = Result
    ATTR_VALUES = success,failure,terminate,<EMPTY>,<MISSING>,<NULL>,<UNFILTERED>
    success -> LogSuccess (output)
    failure -> LogFailure (output)
    terminate -> <Rejected> (output)
LogSuccess (output)
LogFailure (output)
<Rejected> (output)

FME custom transformer ExtractFileFromZip_2

Parameters:
- DESTINATIONFOLDER =
- SOURCEFILE =
- ZIPSOURCEFILE =

INPUT (input)
    -> CreateOutputFolder [FileName]
CreateOutputFolder: FileSystemDeleteMoveCopyExist
    Action = EXIST
    FILEINPUT = @Value(destinationFolder)
    Success -> unZipPython
unZipPython: PythonCaller
    NEW_ATTRIBUTES = _status
    PYTHONSOURCE:
      import fmeobjects
      import zipfile,os.path
      # Template Function interface:
      def processFeature(feature):
          pass

      # Template Class Interface:
      class FeatureProcessor(object):
          #
          # Extracts one file
          #
          def unzipOneFile(self,source_filename,filename,dest_dir):
              zfile = zipfile.ZipFile(source_filename)
              zfile.extract(filename,dest_dir)

          def __init__(self):
              pass
          def input(self,feature):
              source_filename = feature.getAttribute("zipSourceFile")
              filename = feature.getAttribute("sourceFile")
              dest_dir = feature.getAttribute("destinationFolder")
              #
              status = "success"
              # execute unzip
              #self.unzipOneFile(source_filename,filename,dest_dir)
              try:
                  self.unzipOneFile(source_filename,filename,dest_dir)
              except Exception:
                  status="failed"
                  pass
              # set if successfull
              feature.setAttribute("_status",status)
              self.pyoutput(feature)
          def close(self):
              pass
    PYTHONSYMBOL = FeatureProcessor
    -> TestFilter
TestFilter
    DEFAULT_VALUE = FAILED
    TEST_LIST = BOOL_OP,OR,COMPOSITE_TEST,<Unused>,TEST_CLAUSE,"TEST @Value(_status) = success",SUCCESS
    SUCCESS -> SUCCESS (output)
    FAILED -> RemoveFolder [FileName]
    FAILED -> Failed
SUCCESS (output)
RemoveFolder: FileSystemDeleteMoveCopyExist
    Action = EXIST
    FILEINPUT = @Value(destinationFolder)
    Success -> FAILED (output)
    Failed -> FAILED (output)
FAILED (output)
Failed: Inspector [off]

FME custom transformer getMetaDataFromZip
Extracts the meta information from a zip including the nested zip files one level deep.
Zip file to read: The zipfile you wish to read.
Zip files inside this zip file will be extracted using zipfile1_zipfile2.zip as file name. Be aware that zips using folders who have zip files with the same name might overwrite each other in this version.

Parameters:
- inputZipFile =
- scanZipInZip =

InputZip (input)
    -> ParameterFetcher
Note: All none zipped files.
Counter
    CNT_ATTR = fileCounter
    DOMAIN = counter
    SCOPE = Global
    START = 0
    -> Output (output)
Output (output)

Bookmark: Retrieve parameters
ParameterFetcher
    ATTR_LIST = _inputZipFile {$(inputZipFile)} _scanZipInZip {$(scanZipInZip)}
    -> getFilesNamesInZip [zipFile]

Bookmark: First level zip file
getFilesNamesInZip
    sourceZipFile = @Value(_inputZipFile)
    Files -> TestFilter
    Files -> Counter

Bookmark: Test if content is another zip file
TestFilter
    DEFAULT_VALUE = otherFiles
    TEST_LIST:
      BOOL_OP,AND,COMPOSITE_TEST,<Unused>,TEST_CLAUSE,"TEST @Value(fileExtension) = zip
      TEST @Value(_scanZipInZip) = yes",zip in a zip
    zip in a zip -> rootFolder

Bookmark: Compile a targetFolder for the zip file
Note: We need to extract the zip file, we produce a unique name using the basename of the first zip-file and the filename of the internal zip file.
rootFolder: FilenamePartExtractor
    DIRPATH_ATTR = _dirpath
    ROOTNAME_ATTR = _zipBaseName
    SRC_ATTR = @Value(_inputZipFile)
    -> getRootRame
getRootRame: FilenamePartExtractor
    ROOTNAME_ATTR = _rootname
    SRC_ATTR = @Value(zipFileName)
    -> _newZipFolder
_newZipFolder: AttributeCreator
    ATTR_LIST = _newZipFolder,@Value(_dirpath)@Value(_zipBaseName)_@Value(_rootname)
    -> Rem_TempParams
Rem_TempParams: AttributeRemover
    REMOVE_ATTRS = _dirpath,_zipBaseName,_rootname
    -> ExtractFileFromZip

Bookmark: Unzip zip file
ExtractFileFromZip
    DESTINATIONFOLDER = @Value(_newZipFolder)
    SOURCEFILE = @Value(zipFileName)
    ZIPSOURCEFILE = @Value(_inputZipFile)
    SUCCESS -> AttributeCreator
AttributeCreator
    ATTR_LIST = path_windows,@Value(_newZipFolder)\@Value(zipFileName)
    -> AttributeRemover
AttributeRemover
    REMOVE_ATTRS = sourceZipFile,zipFileName,fileCounter,fileExtension,_newZipFolder,zipSourceFile,sourceFile,destinationFolder,action,fileInput,fileOutput,_status
    -> getFilesNames_Zip2 [zipFile]

Bookmark: Get filenames for seccond level zip
getFilesNames_Zip2: getFilesNamesInZip
    sourceZipFile = @Value(path_windows)
    Files -> Counter

FME custom transformer ConvertFMEDataTypesToMSSQLTypes

Parameters:
- FIELDTYPE =
- NAME =

Input (input)
    -> AttributeRenamer
AttributeRenamer
    ATTR_TABLE:
      RENAME_SET_DEFAULT name > FieldName
      RENAME_SET_DEFAULT fme_data_type > FieldType
    -> TestFilter
TestFilter
    DEFAULT_VALUE = SimpleType
    TEST_LIST = BOOL_OP,OR,COMPOSITE_TEST,<Unused>,TEST_CLAUSE,"TEST @Value(FieldType) CONTAINS (",HasPrecisions
    HasPrecisions -> StringSearcher_2
    SimpleType -> AttributeValueMapper
Note: get first part of definition / example fme_varchar or fme_decimal
StringSearcher_2
    CASE = no
    MATCHED_RESULT_ATTR = _fieldtypegroup
    REGEXP = ^\w+
    STRING_TO_SEARCH = @Value(FieldType)
    MATCHED -> StringSearcher_3
Note: get the precision for example 12,0 or 32,10 ..
StringSearcher_3
    CASE = no
    MATCHED_PARTS_ATTR = _fieldprecisions
    MATCHED_RESULT_ATTR = _fieldprecisions
    REGEXP = (\d+),{0,1}(\d{0,})
    STRING_TO_SEARCH = @Value(FieldType)
    MATCHED -> AttributeCreator_2
Note: move to fixed type depending / on syntax
AttributeCreator_2
    ATTR_TABLE = SET_TO _ChangeFieldType = FME_CONDITIONAL:DEFAULT_VALUE'_FME_NO_OP_'BOOL_OP;AND;COMPOSITE_TEST;<Unused>;TEST @Value(FieldType) = fme_decimal;TEST @Value(_fieldprecisions{1}.part) = 0'int'FME_NUM_CONDITIONS2___
    -> AttributeValueMapper_2
Note: Map fme_types with precision syntax
AttributeValueMapper_2
    DIRECTION = Forward (Source To Destination)
    LUT = fme_decimal,numeric,fme_varchar,varchar
    SRC = _fieldtypegroup
    VAL_ATTR = FieldType
    -> AttributeCreator
AttributeCreator
    ATTR_TABLE = SET_TO FieldType = FME_CONDITIONAL:DEFAULT_VALUE'@Value(FieldType)(@Value(_fieldprecisions))'BOOL_OP;OR;COMPOSITE_TEST;<Unused>;TEST @Value(_ChangeFieldType) ATTRIBUTE_HAS_VALUE _FME_BLANK_STRING_'@Value(_ChangeFieldType)'FME_NUM_CONDITIONS2___
    -> Output (output)
Note: Map fme_types without precicion syntax
AttributeValueMapper
    DIRECTION = Forward (Source To Destination)
    LUT = fme_int16,smallint,fme_int8,smallint,fme_uint8,tinyint,fme_uint16,int,fme_int32,int,fme_uint32,bigint,fme_int64,bigint,fme_uint64,bigint,fme_real64,float(53),fme_date,varchar(16),fme_time,varchar(10),fme_boolean,boolean
    SRC = FieldType
    VAL_ATTR = FieldType
    -> Output (output)
Output (output)
