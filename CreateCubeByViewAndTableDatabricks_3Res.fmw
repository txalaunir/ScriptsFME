FME workspace CreateCubeByViewAndTableDatabricks_3Res.fmw
Title: JEDI Cube Generator
Description: Generates the CUBE based on the definitions stored inside the CubeManager database.
The outcome of this FME Workspace is one view and one table. 
The view starts with F_<Cube name>_<Creation date> and contains the join of all dimensions to the grid none aggregated.
The table starts with C_<Cube name>_<Creation date> and contains the aggregated result of all dimensions.
Usage: WARNING:
- After a test I found out that we lose about 10 minutes on the full SQL execution (from 37 min) purly on the functions we have put in place to extract the LON/LAT...
- Our table attributes could as well be improved for example we use as default nvarchar(100) while in many cases we only have 2-10 characters used. I think we should optimize the dimention creation to improve this...
History: 09/08/2016,Jan Bliki,Initial creation of the CUBE scripts,02/02/2016,Jan Bliki,Move dimensions back to original fieldName rarther the Alias.

Parameters:
- CubeId =

Writers:
- MSSQL_JDBC_NONSPATIAL_1: MSSQL_JDBC_NONSPATIAL to CubeManager

Note: Retrieve details of the cube that needs to be build
SQLCreator
    DATASET = CubeManager
    EXPOSED_ATTRIBUTE_LIST = numCubeID
    FORMAT = MSSQL_ADO
    MSSQL_ADO_COMMAND_TIMEOUT = 30
    MSSQL_ADO_NAMED_CONNECTION = CubeManager
    MSSQL_ADO_QUERY_FEATURE_TYPES_FOR_MERGE_FILTERS = Yes
    SQL_STATEMENT:
      SELECT COUNT([dbo].[Cubes].[CubeId]) as numCubeID
      FROM [dbo].[Cubes]
      INNER JOIN [dbo].[CubeFields]
      	on [dbo].[CubeFields].[CubeId] = Cubes.CubeId
         and [dbo].[CubeFields].[LookupFieldId] is Null
      INNER JOIN [dbo].[Fields]
      	on [dbo].[Fields].[FieldId] = [dbo].[CubeFields].[FieldId]
      INNER JOIN [dbo].[Files]
      	on [dbo].[Files].[FileId] = [dbo].[Fields].[FileId]
      INNER JOIN [dbo].[CubeDimensions]
      	on [dbo].[CubeDimensions].[CubeDimensionId] = [dbo].[Files].[CubeDimensionId]
      INNER JOIN [dbo].[GridTypes]
          on [dbo].[GridTypes].[GridTypeId] = [dbo].[Cubes].[GridTypeId]
      INNER JOIN [dbo].[GridTypes] as [DimGridType]
      	on [dbo].[CubeDimensions].[GridTypeId] = [DimGridType].[GridTypeId]
      WHERE [dbo].[Cubes].[CubeId] =$(CubeId)
    RESULT -> VariableSetterNumMode
    RESULT -> AttributeCreator_4 [off]
    <REJECTED> -> SQLExecutor_7 [INITIATOR]
AttributeCreator_4
    ATTR_TABLE:
      SET_TO C_TableName = C_ETC_AQ
      SET_TO CubeId = 212
    -> CallProcessCubeJob_CreateStatistics [DatabrickAPICallerInput]
VariableSetterNumMode
    SCOPE = Global
    VALUE = 0
    VARNAME = varNumMode
    -> Tester_2
Tester_2
    BOOL_OP = OR
    TEST_CLAUSE = TEST @Value(numCubeID) > 0
    TEST_MODE = TEST
    PASSED -> SQLExecutor_6 [INITIATOR]
    FAILED -> SQLExecutor_7 [INITIATOR]
SQLExecutor_6
    COMBINE_ATTRS = Keep Result Attributes if Conflict
    COMBINE_GEOM = Initiator Geometry Only
    DATASET = CubeManager
    EXPOSED_ATTRIBUTE_LIST = CreationDate CubeFieldAlias CubeId Description DimensionShortName DimensionStatus DimGridSpacing DimGridTypeName FieldName GridTypeId GridTypeName HasOverlap Name PrevSQLTableName PrevSQLTableNameAgg PrevSQLTableNameFull SQLDWTableName Title AggregateFunction
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = CubeManager
    MSSQL_ADO_QUERY_FEATURE_TYPES_FOR_MERGE_FILTERS = Yes
    SQL_STATEMENT:
      SELECT [dbo].[Cubes].[CubeId]
            ,[dbo].[Cubes].[GridTypeId]
            ,[dbo].[GridTypes].[Name]         as 'GridTypeName'
      	  ,[DimGridType].[Name]		as 'DimGridTypeName'
      	  ,[DimGridType].[XCellSpacing] as 'DimGridSpacing'
            ,[dbo].[Cubes].[Name]
            ,[dbo].[Cubes].[Title]
            ,[dbo].[Cubes].[Description]
            ,[dbo].[Cubes].[CreationDate]
            ,[dbo].[Cubes].[SQLTableNameFull] as 'PrevSQLTableNameFull'
            ,[dbo].[Cubes].[SQLTableNameAgg]  as 'PrevSQLTableNameAgg'
            ,[dbo].[Cubes].[SQLTableName]     as 'PrevSQLTableName'
      	  ,[dbo].[CubeFields].[CubeFieldAlias] as 'CubeFieldAlias'
            ,[dbo].[CubeFields].[AggregateFunction]
      	  ,IIF(Lower([dbo].[Fields].[Alias])='gridnum','GridNum',[dbo].[Fields].[FieldName]) as 'FieldName'
      	  ,[dbo].[Files].[SQLDWTableName] as 'SQLDWTableName'
      	  ,[dbo].[Files].[StatusPercentage] as 'DimensionStatus'
      	  ,[dbo].[CubeDimensions].[Name]    as 'DimensionShortName'
            ,[dbo].[CubeDimensions].[HasOverlap]
      FROM [dbo].[Cubes]
      INNER JOIN [dbo].[CubeFields]
      	on [dbo].[CubeFields].[CubeId] = Cubes.CubeId
         and [dbo].[CubeFields].[LookupFieldId] is Null
      INNER JOIN [dbo].[Fields]
      	on [dbo].[Fields].[FieldId] = [dbo].[CubeFields].[FieldId]
      INNER JOIN [dbo].[Files]
      	on [dbo].[Files].[FileId] = [dbo].[Fields].[FileId]
      INNER JOIN [dbo].[CubeDimensions]
      	on [dbo].[CubeDimensions].[CubeDimensionId] = [dbo].[Files].[CubeDimensionId]
      INNER JOIN [dbo].[GridTypes]
          on [dbo].[GridTypes].[GridTypeId] = [dbo].[Cubes].[GridTypeId]
      INNER JOIN [dbo].[GridTypes] as [DimGridType]
      	on [dbo].[CubeDimensions].[GridTypeId] = [DimGridType].[GridTypeId]

      WHERE [dbo].[Cubes].[CubeId] =$(CubeId)
      ORDER BY
      	DimGridSpacing,
      	cubefields.DimOrder,
      	Fields.FieldOrder,
      	CubeFieldAlias
    RESULT -> JOB_ID
Note: Store tablenames into the database
SQLExecutorCOmpleted
    COMBINE_ATTRS = Result Attributes Only
    COMBINE_GEOM = Initiator Geometry Only
    DATASET = CubeManager
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = CubeManager
    MSSQL_ADO_QUERY_FEATURE_TYPES_FOR_MERGE_FILTERS = Yes
    SQL_STATEMENT:
      update [dbo].[Cubes]
          set [SQLTableNameFull] = '@Value(F_TableName)',
              [SQLTableNameAgg] = '@Value(C_TableName)',
              [SQLTableName] = '@Value(C_TableName)',
              [StatusPercentage] = 33,
              [TotalAggregatedRecords]=@Value(num_records),
              [FMEJobIdCubeCompilerDate] = getdate(),
              [FMEJobIdCubeStatus]=1,
              [runId] = 0
      where CubeId = @Value(CubeId)
    INITIATOR -> AttributeCreator_2
    INITIATOR -> SQLExecutor_2 [INITIATOR]
    INITIATOR -> JediLogWritter_startjob_9
    <REJECTED> -> AttributeKeeper_2
    <REJECTED> -> AttributeCreator_11
DeleteCubeStats
    CUBEID = @Value(CubeId)
    fields = @Value(fields)
    -> FeatureReader [INITIATOR]
AttributeCreator_2
    ATTR_TABLE:
      SET_TO TransformerPath = SQLExecutorCOmpleted
      SET_TO MessageString = FME workspace completed successfully
    -> AttributeCreator_19_OUTPUT_-__AttributeCreator_18_OUTPUT_-__AttributeCreator_INFO
Note: INFO
AttributeCreator_19_OUTPUT_-__AttributeCreator_18_OUTPUT_-__AttributeCreator_INFO: Junction
    -> AttributeCreator_18_OUTPUT_-__AttributeCreator_INFO
AttributeKeeper_2
    CREATE_BULK_MODE_FEATURES = No
    KEEP_ATTRS = _reader_error
    -> Logger_Error
Logger_Error
    MAXCOORDS = 1
    MAXFEATS = 1
    MESSAGE = ------ ERROR -----
AttributeCreator_11
    ATTR_TABLE:
      SET_TO TransformerPath = SQLExecutor
      SET_TO _error = @Value(_reader_error)
    -> VariableRetriever
Aggregator
    ACCUM_ATTRS_NAME = Drop Incoming Attributes
    AGGREGATE_TYPE = Homogeneous Collection (If Possible)
    GROUP_BY = CubeId
    MODE = Geometry - Assemble One Level
    ORDERED = No
    SEP = ,
    AGGREGATE -> AttributeCreator_16
AttributeCreator_16
    ATTR_TABLE:
      SET_TO TransformerPath = TablesAvailableInSQLDW
      SET_TO MessageString = All dimensions processed
    -> AttributeCreator_17_OUTPUT_-__AttributeCreator_18_OUTPUT_-__AttributeCreator_INFO
Note: INFO
AttributeCreator_17_OUTPUT_-__AttributeCreator_18_OUTPUT_-__AttributeCreator_INFO: Junction
    -> AttributeCreator_18_OUTPUT_-__AttributeCreator_INFO
SQLExecutor_7
    COMBINE_ATTRS = Result Attributes Only
    COMBINE_GEOM = Initiator Geometry Only
    DATASET = CubeManager
    FORMAT = MSSQL_ADO
    MSSQL_ADO_COMMAND_TIMEOUT = 30
    MSSQL_ADO_NAMED_CONNECTION = CubeManager
    MSSQL_ADO_QUERY_FEATURE_TYPES_FOR_MERGE_FILTERS = Yes
    SQL_STATEMENT:
      update [dbo].[Cubes]
          set FMEJobIdCubeCompiler= -1,
          FMEJobIdCubeStatus= 0,
          FMEJobIdCubeCompilerDate = getdate()
      where CubeId = $(CubeId)
    RESULT -> AttributeCreator_21
    INITIATOR -> AttributeCreator_21
    <REJECTED> -> AttributeCreator_21
AttributeCreator_21
    ATTR_TABLE:
      SET_TO MessageString = Error: @Value(_reader_error).
        WorkSpace: $(WORKSPACE_NAME)
      SET_TO TransformerPath = SQLExecutor_5
    -> AttributeCreator_ERROR_2
AttributeCreator_17
    ATTR_TABLE:
      SET_TO MessageString = The cube could not be processed.
      SET_TO TransformerPath = SQLExecutor_7
    -> AttributeCreator_18_OUTPUT_-__AttributeCreator_INFO

Bookmark: Tell DB we are executing the job
Note: Reset the database and provide the job_id so log information can be found easily.
JOB_ID: AttributeCreator
    ATTR_TABLE = SET_TO _FME_JOB_ID = FME_CONDITIONAL:DEFAULT_VALUE'$(FME_JOB_ID)'BOOL_OP;AND;COMPOSITE_TEST;<Unused>;TEST $(FME_JOB_ID) ATTRIBUTE_IS_MISSING _FME_BLANK_STRING_;TEST $(FME_JOB_ID) NOT_ATTRIBUTE_HAS_VALUE _FME_BLANK_STRING_'-1'FME_NUM_CONDITIONS2___
    -> SQLExecutor_5 [INITIATOR]
SQLExecutor_5
    COMBINE_ATTRS = Result Attributes Only
    COMBINE_GEOM = Initiator Geometry Only
    DATASET = CubeManager
    FORMAT = MSSQL_ADO
    MSSQL_ADO_COMMAND_TIMEOUT = 30
    MSSQL_ADO_CREATE_FEATURE_TABLES_FROM_DATA = Yes
    MSSQL_ADO_NAMED_CONNECTION = CubeManager
    MSSQL_ADO_QUERY_FEATURE_TYPES_FOR_MERGE_FILTERS = Yes
    SQL_STATEMENT:
      update [dbo].[Cubes]
          set FMEJobIdCubeCompiler=@Value(_FME_JOB_ID),
              [StatusPercentage] = 0,
              [FMEJobIdCubeCompilerDate] = NULL,
              [FMEJobIdCubeStatus]=0
      where CubeId = @Value(CubeId)
    INITIATOR -> Aggregator
    INITIATOR -> TableNames
    <REJECTED> -> AttributeCreator_21

Bookmark: Name of table to be generated
Note: Generate the names for / G_<TableName>_<Date>_<scale>: (Deleted after process) / Collects all the unique grid cells as one table for each scale / F_<TableName>_<Date>_<scale>: (Deleted after process) / Merged table of all dimensions in the same scale. For example 10km, 1km, 100m / F_<TableName>_<Date>_HighToLow: (Deleted after process) / Merged table of all F_<TableName>_<Date>_<Scale> joined on the most detailed scale. / F_<TableName>_<Date> _A: (Deleted after process) / Aggregate to the lowert level. At this get multiple GridNum's but harmonised on attribute level. / F_<TableName>_<Date> : / View that contains all records including RecordId, GridNum and X,Y / C_<TableName>_<Date> : / Table that contains the aggregated records without GridNum but with RecordId
Note: Create table names
TableNames: AttributeCreator
    ATTR_TABLE:
      SET_TO G_TableName = G_@Value(Name)
      SET_TO F_TableNameHighToLow = F_@Value(Name)_HighToLow
      SET_TO F_TableNameA = F_@Value(Name)_A
      SET_TO F_TableName = F_@Value(Name)
      SET_TO C_TableName = C_@Value(Name)
      SET_TO TMODE_Name = TMODE_@Value(Name)
    -> CreateTSQLScripts

Bookmark: Prepare the T-SQL snippets that will produce the final cube
Note: The following TSQL scripts are created and executed / TSQL For every scale used in the cube (100m,1km,10km): / G_TableTSQL : G_<TableName>_<Date>_<Scale> (22 seconds 5,943,333 records) / F_TableTSQLScale : F_<TableName>_<Date>_<Scale> (9:50 minutes 733,627,213 records for 100m,5:21 minutes for 1km ) / TSQL To join lower scales to detailed scales: / F_TableTSQLHighToLow : G_<TableName>_<Date>_HighToLow (2:35 minutes, 733,627,213 records) / TSQL To bring it all together to the desired scale / F_TableTSQL_A : F_<TableName>_<Date>_A (13:21 minutes, 832,425 records) / F_TableNameTSQL : F_<TableName>_<Date> (1:09 minutes, 6,503,048 records) / TSQL To aggregate on attribute level (removed GridNum and replaced with RecordId) / C_TableTSQL : C_<TableName>_<Date> (11 seconds 785,206 records)
Note: TSQL Creation for the entire process
CreateTSQLScripts
    AGGREGATEFUNCTION = @Value(AggregateFunction)
    CUBEFIELDALIAS = @Value(CubeFieldAlias)
    CUBEID = @Value(CubeId)
    C_TABLENAME = @Value(C_TableName)
    DIMGRIDSPACING = @Value(DimGridSpacing)
    DIMGRIDTYPENAME = @Value(DimGridTypeName)
    DimsPerGroup = 7
    FIELDNAME = @Value(FieldName)
    F_TABLENAME = @Value(F_TableName)
    F_TABLENAMEA = @Value(F_TableNameA)
    F_TABLENAMEHIGHTOLOW = @Value(F_TableNameHighToLow)
    GRIDTYPENAME = @Value(GridTypeName)
    G_TABLENAME = @Value(G_TableName)
    SQLDWTABLENAME = @Value(SQLDWTableName)
    TMODE_NAME = @Value(TMODE_Name)
    TMODE_Name = @Value(TMODE_Name)
    -> Aggregator_2
Note: Group by scale
Aggregator_2
    ACCUM_ATTRS_NAME = Use Attributes From One Feature
    AGGREGATE_TYPE = Homogeneous Collection (If Possible)
    CONCAT_ATTRS = DimensionShortName
    GROUP_BY = DimGridTypeName
    MODE = Geometry - Assemble One Level
    ORDERED = No
    SEP = " \n ,\n "
    AGGREGATE -> Aggregator_5
Aggregator_5
    ACCUM_ATTRS_NAME = Use Attributes From One Feature
    AGGREGATE_TYPE = Homogeneous Collection (If Possible)
    CONCAT_ATTRS = F_TableTSQLScale_Parts
    GROUP_BY = DimGridTypeName
    MODE = Geometry - Assemble One Level
    SEP = ","
    AGGREGATE -> Sorter
Note: Retrieve the unique GridNum values for every scale.
Sorter
    SORT_PARM = DimGridSpacing NUMERIC ASCENDING
    SORTED -> Aggregator_3
Note: Combine all dimensions (tables) into on single table per scale.
Aggregator_3
    ACCUM_ATTRS_NAME = Use Attributes From One Feature
    AGGREGATE_TYPE = Homogeneous Collection (If Possible)
    CONCAT_ATTRS = F_TableTSQLScale G_TableTSQL G_HighToLow_TSQL F_TableTSQLScale_Parts
    MODE = Geometry - Assemble One Level
    SEP = ","
    AGGREGATE -> BuildTSQLArrayJsonParameters
JediLogWritter_startjob_4
    FILEID = $(CubeId)
    MESSAGESTRING = Upload TSQL file to Azure
    MESSAGETYPE = INFO
    OBJECTPROCESSED = Cube
    SQLServerConn = CubeManager
    TRANSFORMERPATH = $(WORKSPACE_NAME)\CreateCubeAndViewDtabaricks
    -> AzureBlobUploader
Note: Send SourceFile to Microsoft Azure
AzureBlobUploader
    ACCOUNT = cwsblobstorage01
    BLOB_NAME = @Value(destFile)
    CONTAINER = cwsblob01
    KEY =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
    SRC_DATA = @Value(_dataset)
    SRC_TYPE = FilePath
    Success -> JediLogWritter_startjob_2
    Success -> Inspector
Inspector

Bookmark: Build JSON parameter for Dtabaricks job
BuildTSQLArrayJsonParameters: AttributeCreator
    ATTR_TABLE:
      SET_TO G_TableTSQL = "@Value(G_TableTSQL)"
      SET_TO F_TableTSQLScale_Part = "@Value(F_TableTSQLScale_Part)"
      SET_TO F_TableTSQLScale = "@Value(F_TableTSQLScale)"
      SET_TO G_HighToLow_TSQL = "@Value(G_HighToLow_TSQL)"
      SET_TO F_TableTSQLHighToLow = "@Value(F_TableTSQLHighToLow)"
      SET_TO C_TableTSQL_MODEs = "@Value(C_TableTSQL_MODEs)"
    -> CreateCubeFields [Initiator]
Note: Databricks API allos JSON params up to 1000kb. TSQL can be longer. To overcome this issue create a text file eith TSQL statements
CreateCubeFields
    CUBEID = @Value(CubeId)
    -> BuildNotebookParameter
BuildNotebookParameter: AttributeCreator
    ATTR_TABLE = SET_TO text_line_data = {"G_TableTSQL":[@Value(G_TableTSQL)],"G_HighToLow_TSQL":[@Value(G_HighToLow_TSQL)], "F_TableTSQLScale_Part":["@Value(F_TableTSQLScale_Parts)"], "F_TableTSQLScale":[@Value(F_TableTSQLScale)],"F_TableTSQLHighToLow": [@Value(F_TableTSQLHighToLow)],"F_TableTSQL_A_Caches":["@Value(CachedModeSubQuery)"],"F_TableTSQL_A_Parts":["@Value(F_TableTSQLA_Part)"],"F_TableTSQL_A": "@Value(F_TableTSQL_A)","F_TableTSQL":"@Value(F_TableTSQL)" ,"C_TableTSQL_MODEs": [@Value(C_TableTSQL_MODEs)],"C_TableTSQL": "@Value(C_TableTSQL)","Fields":"@Value(ColumnName)" }
    -> AttributeKeeper
AttributeKeeper
    CREATE_BULK_MODE_FEATURES = NO
    KEEP_ATTRS = _FME_JOB_ID,C_TableName,C_TableTSQL,CL_TableTSQL,CubeId,DimGridSpacing,DimGridTypeName,F_TableTSQL,F_TableTSQL_A,F_TableTSQLHightToLow,F_TableTSQLScale,G_TableTSQL,Name,SQLDWTableName,Title,F_TableName,CL_TableName,text_line_data
    -> TestFilter
TestFilter
    DEFAULT_VALUE = DEVELOPMENT
    TEST_LIST = "BOOL_OP,OR,COMPOSITE_TEST,""""""1"""""",TEST_CLAUSE,TEST @Value(_FME_JOB_ID) != -1",PRODUCTION
    PRODUCTION -> CreateJsonFilePath
    DEVELOPMENT -> CreateJsonFilePathDebug
Note: Create temp folder to generate the json file
CreateJsonFilePath: TempPathnameCreator
    EXTENSION = .json
    PATHNAME_ATTR = JsonFile
    -> RemoveTabsAndNewLines
CreateJsonFilePathDebug: AttributeCreator
    ATTR_TABLE = SET_TO JsonFile = S:\Common workspace\CrossProjects\Jedi\Bilbomatica\Oskar\Temp\tsgl.json
    -> RemoveTabsAndNewLines
RemoveTabsAndNewLines: StringReplacer
    CASE = NO
    FIND_TEXT = \n|\t|\s{2,}
    NO_MATCH = _FME_NO_OP_
    REGEXP = YES
    REPLACE_TEXT = " "
    SRC_ATTRS = text_line_data
    -> FeatureWriter [text_line]
FeatureWriter
    DATASET = @Value(JsonFile)
    DATASET_ATTR = _dataset
    FEATURE_TYPE_LIST_ATTR = _feature_type
    FORMAT = TEXTLINE
    MORE_SUMMARY_ATTRS = C_TableName F_TableName
    TEXTLINE_COORDINATE_SYSTEM_GRANULARITY = FEATURE
    TEXTLINE_DESTINATION_DATASETTYPE_VALIDATION = Yes
    TEXTLINE_ENCODING = UTF-8
    TEXTLINE_END_OF_LINE = System
    TEXTLINE_MIME_TYPE = text/plain
    TEXTLINE_OVERWRITE_FILE = YES
    TEXTLINE_WRITE_LAST_EOL = YES
    TEXTLINE_WRITE_UTF8_BOM = YES
    TOTAL_FEATURES_WRITTEN_ATTR = _total_features_written
    SUMMARY -> CubeTableNamesAttributeKeeper
CubeTableNamesAttributeKeeper: AttributeCreator
    ATTR_TABLE:
      SET_TO destFile = CubeSourceDataFile/@UUID().json
      SET_TO F_TableName = @Value(_feature_type{0}.F_TableName)
      SET_TO C_TableName = @Value(_feature_type{0}.C_TableName)
      SET_TO CubeId = $(CubeId)
    -> JediLogWritter_startjob_4

Bookmark: Call ProcessCube Databricks Job
JediLogWritter_startjob_2
    FILEID = $(CubeId)
    MESSAGESTRING = Calling RunDatabricksJob
    MESSAGETYPE = INFO
    OBJECTPROCESSED = Cube
    SQLServerConn = CubeManager
    TRANSFORMERPATH = $(WORKSPACE_NAME)\CreateCubeByViewAndTableDatabricks
    -> SQLExecutor_3 [INITIATOR]
Note: Check if there is a RunID in the Database
SQLExecutor_3
    ATTR_IGNORE_NULLS = No
    COMBINE_ATTRS = Keep Initiator Attributes if Conflict
    COMBINE_GEOM = Initiator Geometry Only
    DATASET = CubeManager
    EXPOSED_ATTRIBUTE_LIST = ExecutingRunId
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = CubeManager
    MSSQL_ADO_QUERY_FEATURE_TYPES_FOR_MERGE_FILTERS = Yes
    SQL_STATEMENT:
      SELECT [dbo].[Cubes].[runId] as ExecutingRunId
      FROM [dbo].[Cubes]
      WHERE [dbo].[Cubes].[CubeId] = @Value(CubeId)
    RESULT -> TestFilter_2
TestFilter_2
    DEFAULT_VALUE = <UNFILTERED>
    TEST_LIST = "BOOL_OP,OR,COMPOSITE_TEST,""""""1"""""",TEST_CLAUSE,TEST @Value(ExecutingRunId) != 0",DatabricksRunning,"BOOL_OP,OR,COMPOSITE_TEST,""""""1"""""",TEST_CLAUSE,TEST @Value(ExecutingRunId) = 0",DatabricksNotRunning
    DatabricksRunning -> CheckRunStatus [DatabrickAPICallerInput]
    DatabricksNotRunning -> CallProcessCubeJob [DatabrickAPICallerInput]
CallProcessCubeJob: DatabricksAPICaller
    COMMAND = run-now
    DOMAIN = northeurope.azuredatabricks.net
    JOBID = 11
    METHOD = POST
    PARAMETER = "SQL_Queries_File": "@Value(destFile)"
    TOKEN =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
    CallDatabricksJob_Output -> AttributeRemover
AttributeRemover
    REMOVE_ATTRS = ExecutingRunId
    -> testRunJobError
Note: Check if the Job started correctly
testRunJobError: Tester
    BOOL_OP = OR
    COMPOSITE_TEST = 1 OR 2
    TEST_CLAUSE:
      TEST RunId ATTRIBUTE_IS_MISSING ""
      TEST @Value(RunId) = 0
    TEST_MODE = TEST
    PASSED -> JediLogWritter_startjob_3
    FAILED -> JediLogWritter_startjob_5
JediLogWritter_startjob_3
    FILEID = $(CubeId)
    MESSAGESTRING = RunDatabricksJobError: @Value(error)
    MESSAGETYPE = ERROR
    OBJECTPROCESSED = Cube
    SQLServerConn = CubeManager
    TRANSFORMERPATH = $(WORKSPACE_NAME)\CreateCubeByViewAndTableDatabricks
    -> ErrorRunningJob
ErrorRunningJob: AttributeCreator
    ATTR_TABLE = SET_TO ErrorString = Error running CreateDataFrame job: @Value(error)
    -> VariableRetriever
JediLogWritter_startjob_5
    FILEID = $(CubeId)
    MESSAGESTRING = Waiting for databricks job to complete
    MESSAGETYPE = INFO
    OBJECTPROCESSED = Cube
    SQLServerConn = CubeManager
    TRANSFORMERPATH = $(WORKSPACE_NAME)\CreateCubeByViewAndTableDatabricks
    -> JobStartTimer
Note: In order to checkhow long it takes tp start the cluster
JobStartTimer: AttributeCreator
    ATTR_TABLE = SET_TO StartTime = @DateTimeNow()
    -> SQLExecutor_8 [INITIATOR]
Note: Inserts the RunID in DB to inform that there is a running job in Databricks
SQLExecutor_8
    ATTR_IGNORE_NULLS = No
    COMBINE_ATTRS = Keep Initiator Attributes if Conflict
    COMBINE_GEOM = Initiator Geometry Only
    DATASET = CubeManager
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = CubeManager
    MSSQL_ADO_QUERY_FEATURE_TYPES_FOR_MERGE_FILTERS = Yes
    SQL_STATEMENT:
      update [dbo].[Cubes]
          set [runId] = @Value(RunId)
      where CubeId = @Value(CubeId)
    INITIATOR -> WaitUntilDatabtricksJobCompleted [CheckJobStatus_Input]
Note: Wait until Dtabricks completes or times out to start the cliuster
WaitUntilDatabtricksJobCompleted
    MINUTESTOTIMEOUT = 10
    RUNID = @Value(RunId)
    STARTTIME = @Value(StartTime)
    TestFilter_TERMINATED -> TestJobCompletedSuccessfully
    TestFilter_TERMINATED -> JediLogWritter_startjob_6
TestJobCompletedSuccessfully: Tester
    BOOL_OP = OR
    COMPOSITE_TEST = 1
    TEST_CLAUSE = TEST @Value(noError) = 1
    TEST_MODE = TEST
    PASSED -> AttributeCreator_5
    FAILED -> AttributeCreator_3
AttributeCreator_5
    ATTR_TABLE:
      SET_TO TransformerPath = SQLExecutor
      SET_TO MessageString = @Value(error)
    -> SQLExecutorCOmpleted [INITIATOR]
AttributeCreator_3
    ATTR_TABLE:
      SET_TO TransformerPath = DataBrickJobsCompleted
      SET_TO _error = Error Running PROCESSCUBE notebook
        Cmd:@Value(cmd) Error: @Value(error)
    -> VariableRetriever
JediLogWritter_startjob_6
    FILEID = $(CubeId)
    MESSAGESTRING = Databricks job completed
    MESSAGETYPE = INFO
    OBJECTPROCESSED = Cube
    SQLServerConn = CubeManager
    TRANSFORMERPATH = $(WORKSPACE_NAME)\CreateCubeByViewAndTableDatabricks

Bookmark: Check the run status of the cube in databricks
CheckRunStatus: DatabricksAPICaller
    COMMAND = runs/get-output
    DOMAIN = northeurope.azuredatabricks.net
    METHOD = GET
    RUNID = @Value(ExecutingRunId)
    TOKEN =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
    CallDatabricksJob_Output -> TestJobStatus
TestJobStatus: TestFilter
    DEFAULT_VALUE = <UNFILTERED>
    TEST_LIST = "BOOL_OP,OR,COMPOSITE_TEST,""""""1"""""",TEST_CLAUSE,TEST @Value(status) = PENDING",PENDING,"BOOL_OP,OR,COMPOSITE_TEST,""""""1"""""",TEST_CLAUSE,TEST @Value(status) = RUNNING",RUNNING,"BOOL_OP,OR,COMPOSITE_TEST,""""""1"""""",TEST_CLAUSE,TEST @Value(status) = TERMINATING",TERMINATING,"BOOL_OP,OR,COMPOSITE_TEST,""""""1"""""",TEST_CLAUSE,TEST @Value(status) = TERMINATED",TERMINATED
    PENDING -> CancelRun [DatabrickAPICallerInput]
    RUNNING -> CancelRun [DatabrickAPICallerInput]
    TERMINATING -> CancelRun [DatabrickAPICallerInput]
    TERMINATED -> CallProcessCubeJob [DatabrickAPICallerInput]
    <UNFILTERED> -> CallProcessCubeJob [DatabrickAPICallerInput]
CancelRun: DatabricksAPICaller
    COMMAND = runs/cancel
    DOMAIN = northeurope.azuredatabricks.net
    METHOD = POST
    RUNID = @Value(ExecutingRunId)
    TOKEN =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
    CallDatabricksJob_Output -> CallProcessCubeJob [DatabrickAPICallerInput]

Bookmark: Calculate statistics
JediLogWritter_startjob_9
    FILEID = @Value(CubeId)
    MESSAGESTRING = Calling RunDatabricksJob CreateStatistocs
    MESSAGETYPE = INFO
    OBJECTPROCESSED = Cube
    SQLServerConn = CubeManager
    TRANSFORMERPATH = $(WORKSPACE_NAME)\CreateCubeByViewAndTableDatabricks
    -> CallProcessCubeJob_CreateStatistics [DatabrickAPICallerInput]
CallProcessCubeJob_CreateStatistics: DatabricksAPICaller
    COMMAND = run-now
    DOMAIN = northeurope.azuredatabricks.net
    JOBID = 18
    METHOD = POST
    PARAMETER = "EntityName":"jedi_cubes.@Value(C_TableName)"
    TOKEN =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
    CallDatabricksJob_Output -> testRunJobError_2
Note: Check if the Job started correctly
testRunJobError_2: Tester
    BOOL_OP = OR
    COMPOSITE_TEST = 1 OR 2
    TEST_CLAUSE:
      TEST RunId ATTRIBUTE_IS_MISSING ""
      TEST @Value(RunId) = 0
    TEST_MODE = TEST
    PASSED -> JediLogWritter_startjob_7
    FAILED -> JediLogWritter_startjob_8
JediLogWritter_startjob_7
    FILEID = @Value(CubeId)
    MESSAGESTRING = RunDatabricksJobError: @Value(error)
    MESSAGETYPE = ERROR
    OBJECTPROCESSED = Cube
    SQLServerConn = CubeManager
    TRANSFORMERPATH = $(WORKSPACE_NAME)\CreateCubeByViewAndTableDatabricks
    -> ErrorRunningJob_2
ErrorRunningJob_2: AttributeCreator
    ATTR_TABLE = SET_TO ErrorString = Error running CreateDataFrame job: @Value(error)
JediLogWritter_startjob_8
    FILEID = @Value(CubeId)
    MESSAGESTRING = RunDatabricksJobStarted
    MESSAGETYPE = INFO
    OBJECTPROCESSED = Cube
    SQLServerConn = CubeManager
    TRANSFORMERPATH = $(WORKSPACE_NAME)\CreateDtabricksDim$(WORKSPACE_NAME)\CreateCubeByViewAndTableDatabricksension
    -> JobStartTimer_2
Note: In order to checkhow long it takes tp start the cluster
JobStartTimer_2: AttributeCreator
    ATTR_TABLE = SET_TO StartTime = @DateTimeNow()
    -> WaitUntilDatabtricksJobCompleted_2 [CheckJobStatus_Input]
Note: Wait until Dtabricks completes or times out to start the cliuster
WaitUntilDatabtricksJobCompleted_2
    MINUTESTOTIMEOUT = 20
    RUNID = @Value(RunId)
    STARTTIME = @Value(StartTime)
    TestFilter_TERMINATED -> TestJobSuccess_2
    TestFilter_TERMINATED -> JediLogWritter_startjob_10
TestJobSuccess_2: Tester
    BOOL_OP = OR
    COMPOSITE_TEST = 1
    TEST_CLAUSE = TEST @Value(noError) = 1
    TEST_MODE = TEST
    PASSED -> DeleteCubeStats [Initiator]
JediLogWritter_startjob_10
    FILEID = @Value(CubeId)
    MESSAGESTRING = Databricks job completed
    MESSAGETYPE = INFO
    OBJECTPROCESSED = Cube
    SQLServerConn = CubeManager
    TRANSFORMERPATH = $(WORKSPACE_NAME)\CreateCubeByViewAndTableDatabricks

Bookmark: Download and parse JSON from BlobStorage
FeatureReader
    ATTR_ACCUM_MODE = Only Use Result
    COMBINE_GEOM = Use Result
    DATASET = https://cwsblobstorage01.blob.core.windows.net/cwsblob01/statistics/@Value(C_TableName).json
    FORMAT = JSON
    JSON_DECODE_TEXT_STRINGS = Yes
    JSON_FEATURE_TYPE_KEY = json_featuretype
    JSON_FLATTEN_MODE = ALL_LEVELS
    JSON_GEOMETRY_FORMAT = None
    JSON_SAVE_FRAGMENTS = NO
    JSON_SCAN_MODE = AUTO
    JSON_USE_BASENAME_AS_DEFAULT_FEATURE_TYPE = No
    JSON_USE_SEARCH_ENVELOPE = NO
    OUTPUT_FEATURES_DISPLAY = Schema and Data Features
    <OTHER> -> AttributeExposer
    INITIATOR -> AttributeCreator_6
    <REJECTED> -> JediLogWritter_startjob_15
AttributeExposer
    ATTR_LIST = fieldname,fieldValue,grouporder,TotalRecord
    -> AttributeKeeper_6
AttributeKeeper_6
    CREATE_BULK_MODE_FEATURES = NO
    KEEP_ATTRS = fieldname,fieldValue,grouporder,TotalRecord
    -> ParameterFetcher

Bookmark: Field Statistcis
ParameterFetcher
    ATTR_LIST = CubeId $(CubeId)
    -> SQLExecutor [INITIATOR]
SQLExecutor
    COMBINE_ATTRS = Result Attributes Only
    COMBINE_GEOM = Initiator Geometry Only
    DATASET = CubeManager
    EXPOSED_ATTRIBUTE_LIST = CubeFieldId CubeFieldAlias FieldValue GroupOrder TotalRecords
    FORMAT = MSSQL_JDBC_NONSPATIAL
    MSSQL_JDBC_NONSPATIAL_NAMED_CONNECTION = CubeManager
    MSSQL_JDBC_NONSPATIAL_QUERY_FEATURE_TYPES_FOR_MERGE_FILTERS = Yes
    MSSQL_JDBC_NONSPATIAL_QUERY_TIMEOUT = 30
    SQL_STATEMENT:
      select CubeFieldId,CubeFieldAlias, '@ReplaceString(@Value(fieldValue),','')' as FieldValue, @Value(grouporder) as GroupOrder, @Value(TotalRecord) as TotalRecords
      from
      	CubeFields
      where cubeid  = @Value(CubeId) and LookupFieldId is null and CubeFieldAlias = '@Value(fieldname)'
    RESULT -> CubeFieldStatistics (writer MSSQL_JDBC_NONSPATIAL_1)
    <REJECTED> -> JediLogWritter_startjob_14
CubeFieldStatistics (writer MSSQL_JDBC_NONSPATIAL_1)
    attributes: CubeFieldId bigint, FieldValue varchar(500), TotalRecords bigint, GroupOrder integer
JediLogWritter_startjob_14
    FILEID = @Value(CubeId)
    MESSAGESTRING = SQLExecutorRejected
    MESSAGETYPE = WARNING
    OBJECTPROCESSED = Cube
    SQLServerConn = CubeManager
    TRANSFORMERPATH = $(WORKSPACE_NAME)\CreateCubeByViewAndTableDatabricks
JediLogWritter_startjob_15
    FILEID = @Value(CubeId)
    MESSAGESTRING = JSON with stats doesn't exist
    MESSAGETYPE = WARNING
    OBJECTPROCESSED = Cube
    SQLServerConn = CubeManager
    TRANSFORMERPATH = $(WORKSPACE_NAME)\CreateCubeByViewAndTableDatabricks

Bookmark: Delete JSON from BlobStorage once read
AttributeCreator_6
    ATTR_TABLE = SET_TO JSONPathInBlobStorage = statistics/@Value(C_TableName).json
    -> AzureBlobStorageConnector
AzureBlobStorageConnector
    CREDENTIAL_SOURCE = WEBCONN
    OPERATION_TYPE = Delete
    PARAMETER_SETUP = _FME_AZURE_CONTAINER]cwsblob01]_FME_FILEID]@Value(JSONPathInBlobStorage)]FME_CONTROLLER_QUERY_FILE]azureblobstorageconnector_deps/Delete.fme
    _FME_AZURE_CONNECTION = JEDI Azure Storage Esparza

Bookmark: Update event log and UpdatedDate
SQLExecutor_2
    COMBINE_ATTRS = Result Attributes Only
    COMBINE_GEOM = Initiator Geometry Only
    DATASET = CubeManager
    FORMAT = MSSQL_ADO
    MSSQL_ADO_COMMAND_TIMEOUT = 30
    MSSQL_ADO_CREATE_FEATURE_TABLES_FROM_DATA = Yes
    MSSQL_ADO_NAMED_CONNECTION = CubeManager
    MSSQL_ADO_QUERY_FEATURE_TYPES_FOR_MERGE_FILTERS = Yes
    SQL_STATEMENT:
      	insert into EventLog (DateTime,[Username],[EntityType],[EntityId],[FileId],[Operation]  )
      	values (
      		getdate(),
      		'FME',
      		'Cube',
      		@Value(CubeId),
      		0,
      		'Updated')

Bookmark: WRITE ERROR
Note: All temp tables are kept until ready for delete.
VariableRetriever
    SCOPE = Global
    VALUE_ATTR = StatusPercentage
    VARNAME = _StatusPercentage
    -> AttributeCreator
AttributeCreator
    ATTR_TABLE = SET_TO StatusPercentage = FME_CONDITIONAL:DEFAULT_VALUE'@Evaluate(@Value(StatusPercentage)+10)'BOOL_OP;OR;COMPOSITE_TEST;<Unused>;TEST StatusPercentage NOT_ATTRIBUTE_HAS_A_VALUE _FME_BLANK_STRING_'10'FME_NUM_CONDITIONS2___
    -> VariableSetter
VariableSetter
    SCOPE = Global
    VALUE = @Value(StatusPercentage)
    VARNAME = _StatusPercentage
    -> StringReplacer_5
StringReplacer_5
    CASE = NO
    FIND_TEXT = '
    NO_MATCH = _FME_NO_OP_
    REGEXP = NO
    REPLACE_TEXT = "
    SRC_ATTRS = _error
    -> AttributeKeeper_3
AttributeKeeper_3
    CREATE_BULK_MODE_FEATURES = No
    KEEP_ATTRS = CL_TableName,F_TableName,CubeId,_error,C_TableName,StatusPercentage
    -> Logger_4
Logger_4
    MAXCOORDS = 1
    MAXFEATS = 1
    MESSAGE = -------------------------------- ERROR---------------------
    LOGGED -> SQLExecutor_4 [INITIATOR]
Note: Write Error to log attribute
SQLExecutor_4
    COMBINE_ATTRS = Keep Initiator Attributes if Conflict
    COMBINE_GEOM = Initiator Geometry Only
    DATASET = CubeManager
    FORMAT = MSSQL_ADO
    MSSQL_ADO_COMMAND_TIMEOUT = 30
    MSSQL_ADO_CREATE_FEATURE_TABLES_FROM_DATA = Yes
    MSSQL_ADO_NAMED_CONNECTION = CubeManager
    MSSQL_ADO_QUERY_FEATURE_TYPES_FOR_MERGE_FILTERS = Yes
    SQL_STATEMENT:
      UPDATE dbo.Cubes
          set ErrorMessages = ISNULL(ErrorMessages,'') + ' @Value(_error)',
              FMEJobIdCubeStatus=0,
              TotalAggregatedRecords=Null,
              StatusPercentage=@Value(StatusPercentage)
      WHERE CubeId = @Value(CubeId)
    INITIATOR -> AttributeCreator_15
    <REJECTED> -> AttributeCreator_14
AttributeCreator_15
    ATTR_TABLE:
      SET_TO MessageString = Error: @Value(_error).
        WorkSpace: $(WORKSPACE_NAME)
        Transformer name: @Value(_error)
    -> AttributeCreator_ERROR_2
AttributeCreator_14
    ATTR_TABLE:
      SET_TO MessageString = Error: @Value(_reader_error).
        WorkSpace: $(WORKSPACE_NAME)
        Transformer name: @Value(_reader_error)
      SET_TO TransformerPath = SQLExecutor_4
    -> AttributeCreator_ERROR_2

Bookmark: Write Logger
AttributeCreator_ERROR_2: Junction
    -> AttributeCreator_ERROR
AttributeCreator_ERROR
    ATTR_TABLE = SET_TO MessageType = ERROR
    -> AttributeKeeper_4
AttributeCreator_18_OUTPUT_-__AttributeCreator_INFO: Junction
    -> AttributeCreator_INFO
AttributeCreator_INFO
    ATTR_TABLE = SET_TO MessageType = INFO
    -> AttributeKeeper_4
AttributeKeeper_4
    CREATE_BULK_MODE_FEATURES = No
    KEEP_ATTRS = TransformerPath,CubeId,MessageString,MessageType
    -> JediLogWritter
JediLogWritter
    FILEID = $(CubeId)
    MESSAGESTRING = @Value(MessageString)
    MESSAGETYPE = @Value(MessageType)
    OBJECTPROCESSED = Cube
    SQLServerConn = CubeManager
    TRANSFORMERPATH = $(WORKSPACE_NAME)\StepA: CREATE CUBE\@Value(TransformerPath)
    -> Tester
Tester
    BOOL_OP = OR
    TEST_CLAUSE = TEST @Value(MessageType) = ERROR
    TEST_MODE = TEST
    PASSED -> Terminator_2
Terminator_2 [off]
    MESSAGE = Translation Terminated: @Value(MessageString)

FME custom transformer SQLFieldNameCompiler_NoSizes

Parameters:
- AddAfterField =
- AggregateFunction =
- DatabaseOwner =
- FieldAlias =
- FieldName =
- GROUP_BY =
- TableName =
- TargetAttribute =
- TotalIndents =

Input (input)
    -> Counter
Counter
    CNT_ATTR = _count
    DOMAIN = counter
    SCOPE = Local
    START = 0
    -> StringSearcher
    -> FeatureMerger [REQUESTOR]
Note: TargetAttribute receiving the final result
StringSearcher
    CASE = no
    MATCHED_RESULT_ATTR = $(TargetAttribute)
    REGEXP = a
    STRING_TO_SEARCH = a
    MATCHED -> ParameterFetcher
ParameterFetcher
    ATTR_LIST = _FieldAlias $(FieldAlias) _FieldName $(FieldName) _TableName $(TableName) _TargetAttribute $(TargetAttribute) _DatabaseOwner $(DatabaseOwner) _TotalIndents $(TotalIndents) _AddAfterField $(AddAfterField) _AggregateFunction $(AggregateFunction)
    -> AttributeCreator_3
Note: Compile SQL syntax depending / on the informaton provided / [Database owner]
AttributeCreator_3
    ATTR_TABLE = SET_TO __SQLFieldNames = FME_CONDITIONAL:DEFAULT_VALUE''BOOL_OP;AND;COMPOSITE_TEST;1;TEST @Value(_DatabaseOwner) ATTRIBUTE_HAS_VALUE _FME_BLANK_STRING_'@Value(_DatabaseOwner).'FME_NUM_CONDITIONS2___
    -> AttributeCreator_4
Note: Compile SQL syntax depending / on the informaton provided / [TableName].[FieldName]
AttributeCreator_4
    ATTR_TABLE = SET_TO __SQLFieldNames = FME_CONDITIONAL:DEFAULT_VALUE'`@LowerCase(@Value(_FieldName))`'BOOL_OP;AND;COMPOSITE_TEST;<Unused>;TEST @Value(_TableName) ATTRIBUTE_HAS_VALUE _FME_BLANK_STRING_'@LowerCase(@Value(__SQLFieldNames))`@Value(_TableName)`.`@LowerCase(@Value(_FieldName))`'FME_NUM_CONDITIONS2___
    -> TestFilter
Note: Do we make a count or sum / on this field?
TestFilter
    DEFAULT_VALUE = Plain
    TEST_LIST = BOOL_OP,OR,COMPOSITE_TEST,<Unused>,TEST_CLAUSE,"TEST @Value(_AggregateFunction) ATTRIBUTE_HAS_VALUE """"",Agregate
    Agregate -> IS_MODE
    Plain -> AttributeCreator
IS_MODE: TestFilter
    DEFAULT_VALUE = AGG
    TEST_LIST = "BOOL_OP,OR,COMPOSITE_TEST,""""""1"""""",TEST_CLAUSE,TEST @Value(_AggregateFunction) = MODE",MODE
    MODE -> AttributeCreator_7
    AGG -> AttributeCreator_5
Note: Buid Field, count(Filed)
AttributeCreator_7
    ATTR_TABLE = SET_TO __SQLFieldNames = FME_CONDITIONAL:DEFAULT_VALUE'@LowerCase(@Value(__SQLFieldNames)) as `@LowerCase(@Trim(@Value(_FieldName)))`'BOOL_OP;AND;COMPOSITE_TEST;1;TEST _FieldAlias ATTRIBUTE_HAS_A_VALUE _FME_BLANK_STRING_'@LowerCase(@Value(__SQLFieldNames)) as `@LowerCase(@Trim(@Value(_FieldAlias)))`'FME_NUM_CONDITIONS2___
    -> AttributeCreator_2
Note: Wrap the aggregate function arround / the field and set Alias is provided
AttributeCreator_5
    ATTR_TABLE = SET_TO __SQLFieldNames = FME_CONDITIONAL:DEFAULT_VALUE'@Value(_AggregateFunction)(@LowerCase(@Value(__SQLFieldNames))) as `@LowerCase(@Trim(@Value(_FieldName)))`'BOOL_OP;AND;COMPOSITE_TEST;<Unused>;TEST @Value(_FieldAlias) ATTRIBUTE_HAS_VALUE _FME_BLANK_STRING_'@Value(_AggregateFunction)(@LowerCase(@Value(__SQLFieldNames)))   as `@LowerCase(@Trim(@Value(_FieldAlias)))`'FME_NUM_CONDITIONS2___
    -> AttributeCreator_2
Note: Compile SQL syntax depending / on the informaton provided / as [Alias]
AttributeCreator
    ATTR_TABLE = SET_TO __SQLFieldNames = FME_CONDITIONAL:DEFAULT_VALUE'@Value(__SQLFieldNames)'BOOL_OP;AND;COMPOSITE_TEST;1;TEST @Value(_FieldAlias) ATTRIBUTE_HAS_VALUE _FME_BLANK_STRING_'@LowerCase(@Value(__SQLFieldNames)) as `@LowerCase(@Trim(@Value(_FieldAlias)))`'FME_NUM_CONDITIONS2___
    -> AttributeCreator_2
Note: Add something after field
AttributeCreator_2
    ATTR_TABLE = SET_TO __SQLFieldNames = FME_CONDITIONAL:DEFAULT_VALUE'_FME_NO_OP_'BOOL_OP;OR;COMPOSITE_TEST;<Unused>;TEST @Value(_AddAfterField) ATTRIBUTE_HAS_VALUE _FME_BLANK_STRING_'@Value(__SQLFieldNames) @Value(_AddAfterField)'FME_NUM_CONDITIONS2___
    -> StringPadder
Note: Add indents to make the / TSQL look nice
StringPadder
    BLANK_ATTRIBUTE = Yes
    PADCHAR = "\t"
    SIDE = Left
    SRC_ATTRS = __SQLFieldNames
    WIDTH = @Value(_TotalIndents)+@StringLength(@Value(__SQLFieldNames))
    -> Aggregator_2
Note: Make field snippeds unqiue
Aggregator_2
    ACCUM_ATTRS_NAME = Use Attributes From One Feature
    AGGREGATE_TYPE = Homogeneous Collection (If Possible)
    GROUP_BY = __SQLFieldNames
    MODE = Geometry - Assemble One Level
    ORDERED = No
    SEP = ,
    AGGREGATE -> Sorter
Note: Make sure we order / as they came in
Sorter
    SORT_PARM = _count NUMERIC ASCENDING
    SORTED -> Aggregator
Note: Combine them all together
Aggregator
    ACCUM_ATTRS_NAME = Use Attributes From One Feature
    AGGREGATE_TYPE = Homogeneous Collection (If Possible)
    CONCAT_ATTRS = __SQLFieldNames
    GROUP_BY = $(GROUP_BY)
    MODE = Geometry - Assemble One Level
    ORDERED = No
    SEP = ",\n"
    AGGREGATE -> PythonCaller
Note: Set to users attribute
PythonCaller
    PYTHONSOURCE:
      import fme
      import fmeobjects
      # Template Function interface:
      # When using this function, make sure its name is set as the value of
      # the 'Class or Function to Process Features' transformer parameter
      def processFeature(feature):
          pass

      # Template Class Interface:
      # When using this class, make sure its name is set as the value of
      # the 'Class or Function to Process Features' transformer parameter
      class FeatureProcessor(object):
          def __init__(self):
              pass
          def input(self,feature):
              #
              # Move the new value into the target attribute user has chosen.
              #
              TargetAttribute = feature.getAttribute("_TargetAttribute")
              SQLFieldNames = feature.getAttribute("__SQLFieldNames")
              feature.setAttribute(TargetAttribute,SQLFieldNames)
              self.pyoutput(feature)
          def close(self):
              pass
    PYTHONSYMBOL = FeatureProcessor
    -> AttributeRemover
AttributeRemover
    REMOVE_ATTRS = _AddAfterField,_TableName,_DatabaseOwner,_FieldAlias,__SQLFieldNames,_AggregateFunction,_FieldName,_TargetAttribute
    -> FeatureMerger [SUPPLIER]
Note: Remap new value to all values
FeatureMerger
    ATTR_ACCUM_MODE = Merge Supplier
    ATTR_CONFLICT_RES = Use Requestor
    CLEANING_TOLERANCE = None
    GROUP_BY = $(GROUP_BY)
    IGNORE_NULLS = No
    JOIN_KEYS = 1 1 AUTO
    MERGE_TYPE = Attributes Only
    PROCESS_DUPS = No
    REJECT_NULL_MISSING_KEYS = No
    SUPPLIERS_FIRST = No
    MERGED -> Output (output)
Output (output)

FME custom transformer SQLJoinCompiler
Creates an SQL snipped that represents a JOIN in a database.
Parameters:
    Group by: You can group a set of records that should each compile its set of JOIN snippeds
    Join type: The type of JOIN you wish to create (LEFT,RIGHT,CROSS,INNER)
    Database owner: The database owner to use, default is 'dbo' (optional)
    Join table name: The table that will be joined. This table name will come just after the LEFT JOIN <table name>
    Join field name: The field name we will use to compare the join towards.
    Source table name: The table we join against. For example the table just after the FROM <table name>
    Source field name: The field name we will use to compare the join towards.
    Target attribute: The attribute that will receive the full JOIN snipped.
    Explenation:
If you have complex SQL statements that are generated by FME then this transforer is excelent. The input is a number of features that together should generate one or more JOIN snippeds. The result will be an additional attribute added to the input features. This allows you to perform a number of snippeds and at the end perform an aggregate or sample the first record. 
An example of such snipped would look like this.
LEFT JOIN [D_CoastelZones_2016_7_11_1km]
    ON [D_CoastelZones_2016_7_11_1km].[GridNum] = [G_LEAC18_18_11_2016].[GridNum]
LEFT JOIN [D_EBK_2016_7_11_1km]
    ON [D_EBK_2016_7_11_1km].[GridNum] = [G_LEAC18_18_11_2016].[GridNum]
LEFT JOIN [D_WFD_2016_7_11_1km]
    ON [D_WFD_2016_7_11_1km].[GridNum] = [G_LEAC18_18_11_2016].[GridNum]
LEFT JOIN [D_NUTS_2016_7_12_1km]
    ON [D_NUTS_2016_7_12_1km].[GridNum] = [G_LEAC18_18_11_2016].[GridNum]
LEFT JOIN [D_A_CLC_90_56_20161115_100m]
    ON [D_A_CLC_90_56_20161115_100m].[GridNum] = [G_LEAC18_18_11_2016].[GridNum]
LEFT JOIN [D_A_CLC_00_57_20161115_100m]
    ON [D_A_CLC_00_57_20161115_100m].[GridNum] = [G_LEAC18_18_11_2016].[GridNum]
LEFT JOIN [D_A_CLC_06_58_20161115_100m]
    ON [D_A_CLC_06_58_20161115_100m].[GridNum] = [G_LEAC18_18_11_2016].[GridNum]
LEFT JOIN [D_A_CLC_12_59_20161115_100m]
    ON [D_A_CLC_12_59_20161115_100m].[GridNum] = [G_LEAC18_18_11_2016].[GridNum]

Parameters:
- DIMGRIDTYPENAME =
- DatabaseOwner =
- DimsPerGroup =
- Group_by =
- Join_Field_Name =
- Join_Table_Name =
- Join_Type =
- Source_Field_Name =
- Source_Table_Name =
- TargetAttribute =
- TotalIndents =

Input (input)
    -> StringSearcher_2
Note: TargetAttribute receiving the final result
StringSearcher_2
    CASE = no
    MATCHED_RESULT_ATTR = $(TargetAttribute)
    REGEXP = a
    STRING_TO_SEARCH = a
    MATCHED -> ParameterFetcher_2
ParameterFetcher_2
    ATTR_LIST = _DatabaseOwner $(DatabaseOwner) _Join_Field_Name $(Join_Field_Name) _Join_Table_Name $(Join_Table_Name) _Join_Type $(Join_Type) _Source_Field_Name $(Source_Field_Name) _Source_Table_Name $(Source_Table_Name) _TargetAttribute $(TargetAttribute) _TotalIndents $(TotalIndents) _GROUP_BY $(Group_by)
    -> Aggregator
    -> FeatureMerger [REQUESTOR]
Note: We only extract the unique tables
Aggregator
    ACCUM_ATTRS_NAME = Use Attributes From One Feature
    AGGREGATE_TYPE = Homogeneous Collection (If Possible)
    GROUP_BY = _Join_Table_Name _Source_Table_Name
    MODE = Geometry - Assemble One Level
    ORDERED = No
    SEP = ,
    AGGREGATE -> Sorter
Sorter
    SORT_PARM = _GROUP_BY ALPHA DESCENDING _Join_Table_Name ALPHA ASCENDING
    SORTED -> ProduceSQLJOINString
ProduceSQLJOINString
    _DATABASEOWNER = @Value(_DatabaseOwner)
    _JOIN_FIELD_NAME = @Value(_Join_Field_Name)
    _JOIN_TABLE_NAME = @Value(_Join_Table_Name)
    _JOIN_TYPE = @Value(_Join_Type)
    _SOURCE_FIELD_NAME = @Value(_Source_Field_Name)
    _SOURCE_TABLE_NAME = @Value(_Source_Table_Name)
    _TOTALINDENTS = @Value(_TotalIndents)
    -> StringPadder_2
Note: Add indents to make the / TSQL look nice
StringPadder_2
    BLANK_ATTRIBUTE = Yes
    PADCHAR = "\t"
    SIDE = Left
    SRC_ATTRS = __SQLJoin
    WIDTH = @Value(_TotalIndents)+@StringLength(@Value(__SQLJoin))
    -> TestFilter_2
TestFilter_2
    DEFAULT_VALUE = Empty
    TEST_LIST = BOOL_OP,OR,COMPOSITE_TEST,<Unused>,TEST_CLAUSE,"TEST __SQLJoin ATTRIBUTE_HAS_VALUE """"",Filled
    Filled -> TestFilter_3
Note: Set to users attribute
PythonCaller_2
    PYTHONSOURCE:
      import fme
      import fmeobjects
      # Template Function interface:
      # When using this function, make sure its name is set as the value of
      # the 'Class or Function to Process Features' transformer parameter
      def processFeature(feature):
          pass

      # Template Class Interface:
      # When using this class, make sure its name is set as the value of
      # the 'Class or Function to Process Features' transformer parameter
      class FeatureProcessor(object):
          def __init__(self):
              pass
          def input(self,feature):
              #
              # Move the new value into the target attribute user has chosen.
              #
              TargetAttribute = feature.getAttribute("_TargetAttribute")
              SQLJoin = feature.getAttribute("__SQLJoin")
              feature.setAttribute(TargetAttribute,SQLJoin)
              self.pyoutput(feature)
          def close(self):
              pass
    PYTHONSYMBOL = FeatureProcessor
    -> AttributeCreator_2
AttributeCreator_2
    ATTR_TABLE = SET_TO SQLJoin = @Value(__SQLJoin)
    -> AttributeRemover_2
AttributeRemover_2
    REMOVE_ATTRS = __SQLJoin,_DatabaseOwner,_Source_Field_Name,_Join_Field_Name,_Source_Table_Name,_TargetAttribute,_Join_Table_Name,_Join_Type,_count
    -> FeatureMerger [SUPPLIER]
Note: Remap new value to all values
FeatureMerger
    ATTR_ACCUM_MODE = Merge Supplier
    ATTR_CONFLICT_RES = Use Requestor
    GROUP_BY = _GROUP_BY NumGroup
    IGNORE_NULLS = No
    JOIN_KEYS = 1 1 AUTO
    MERGE_TYPE = Attributes Only
    PROCESS_DUPS = NO
    REJECT_NULL_MISSING_KEYS = No
    SUPPLIERS_FIRST = No
    MERGED -> Output (output)
Output (output)

Bookmark: Create left join clauses for F_Scale, each with a parametrized number of dimensions
TestFilter_3
    DEFAULT_VALUE = <UNFILTERED>
    TEST_LIST = "BOOL_OP,OR,COMPOSITE_TEST,""""""1"""""",TEST_CLAUSE,TEST @Value(DimGridTypeName) = 10m",10m,"BOOL_OP,OR,COMPOSITE_TEST,""""""1"""""",TEST_CLAUSE,TEST @Value(DimGridTypeName) = 100m",100m,"BOOL_OP,OR,COMPOSITE_TEST,""""""1"""""",TEST_CLAUSE,TEST @Value(DimGridTypeName) = 1km",1km,"BOOL_OP,OR,COMPOSITE_TEST,""""""1"""""",TEST_CLAUSE,TEST @Value(DimGridTypeName) = 10km",10km
    10m -> Counter_2
    100m -> Counter_3
    1km -> Counter_4
    10km -> Counter_5
Counter_2
    CNT_ATTR = _count
    DOMAIN = counter10m
    SCOPE = Local
    START = 1
    -> AttributeCreator
Counter_3
    CNT_ATTR = _count
    DOMAIN = counter100m
    SCOPE = Local
    START = 1
    -> AttributeCreator
Counter_4
    CNT_ATTR = _count
    DOMAIN = counter1km
    SCOPE = Local
    START = 1
    -> AttributeCreator
Counter_5
    CNT_ATTR = _count
    DOMAIN = counter10km
    SCOPE = Local
    START = 1
    -> AttributeCreator
AttributeCreator
    ATTR_TABLE = SET_TO NumGroup = @Evaluate(@int(@Value(_count)/$(DimsPerGroup)))
    -> Aggregator_2
Note: Combine them all together
Aggregator_2
    ACCUM_ATTRS_NAME = Use Attributes From One Feature
    AGGREGATE_TYPE = Homogeneous Collection (If Possible)
    CONCAT_ATTRS = __SQLJoin
    GROUP_BY = NumGroup _GROUP_BY
    MODE = Geometry - Assemble One Level
    ORDERED = Yes
    SEP = "\n"
    AGGREGATE -> PythonCaller_2

FME custom transformer BuildCTableModeQuery

Parameters:
- AddAfterField =
- AddGridNums =
- AggregateFunction =
- DatabaseOwner =
- FieldName =
- NOMODEFIELDS =
- TMODE_NAME =
- TableName =
- TargetAttribute =
- TotalIndents =

Input_2 (input)
    -> AttributeCreator_3
AttributeCreator_3
    ATTR_TABLE = SET_TO NoModeFieldsAux = @Value(NoModeFields)
    -> StringReplacer
StringReplacer
    CASE = NO
    FIND_TEXT = `TMODE_[a-z,\,A-Z,_, ,\.,0-9,\-,\(,\),\)]{1,}`\.
    NO_MATCH = _FME_NO_OP_
    REGEXP = YES
    SRC_ATTRS = NoModeFieldsAux
    -> Counter
Counter
    CNT_ATTR = _count
    DOMAIN = counter
    SCOPE = Local
    START = 0
    -> StringSearcher
    -> FeatureMerger [REQUESTOR]
Note: TargetAttribute receiving the final result
StringSearcher
    CASE = no
    MATCHED_RESULT_ATTR = $(TargetAttribute)
    REGEXP = a
    STRING_TO_SEARCH = a
    MATCHED -> ParameterFetcher
ParameterFetcher
    ATTR_LIST = _FieldName $(FieldName) _TableName $(TableName) _TargetAttribute $(TargetAttribute) _DatabaseOwner $(DatabaseOwner) _TotalIndents $(TotalIndents) _AddAfterField $(AddAfterField) _AggregateFunction $(AggregateFunction)
    -> AttributeCreator
AttributeCreator
    ATTR_TABLE:
      SET_TO GridNumCond = FME_CONDITIONAL:DEFAULT_VALUE' 'BOOL_OP;OR;COMPOSITE_TEST;1;TEST $(AddGridNums) = Yes'    jedi_cubes.@Value(_TableName).GridNum10km = `@Value(TMODE_Name)_C_@Value(_FieldName)`.GRIDNUM10Km AND
            jedi_cubes.@Value(_TableName).GridNum = `@Value(TMODE_Name)_C_@Value(_FieldName)`.GRIDNUM AND 'FME_NUM_CONDITIONS2___
      SET_TO TAGridNumCond = FME_CONDITIONAL:DEFAULT_VALUE' 'BOOL_OP;OR;COMPOSITE_TEST;1;TEST $(AddGridNums) = Yes'        TA.`GridNum10km`,
                TA.`GridNum`,'FME_NUM_CONDITIONS2___
      SET_TO T1GridNumCond = FME_CONDITIONAL:DEFAULT_VALUE' 'BOOL_OP;OR;COMPOSITE_TEST;1;TEST $(AddGridNums) = Yes'		T1.`GridNum10km`,
                T1.`GridNum`,
        'FME_NUM_CONDITIONS2___
    -> CreateInnerQueryFields
CreateInnerQueryFields: AttributeCreator
    ATTR_TABLE:
      SET_TO TAFields = @ReplaceString(@ReplaceString(@Value(NoModeFieldsAux),`@Value(_TableName)`,TA),"jedi_cubes.","")
      SET_TO T1Fields = @ReplaceString(@ReplaceString(@Value(NoModeFieldsAux),`@Value(_TableName)`,T1),"jedi_cubes.","")
    -> TestFilter
Note: Do we make a count or sum / on this field?
TestFilter
    DEFAULT_VALUE = Plain
    TEST_LIST = "BOOL_OP,OR,COMPOSITE_TEST,""""""1"""""",TEST_CLAUSE,TEST _AggregateFunction ATTRIBUTE_HAS_A_VALUE """,Agregate
    Agregate -> IS_MODE
    Plain -> AttributeCreator_2
IS_MODE: TestFilter
    DEFAULT_VALUE = AGG
    TEST_LIST = "BOOL_OP,OR,COMPOSITE_TEST,""""""1"""""",TEST_CLAUSE,TEST @Value(_AggregateFunction) = MODE",MODE
    MODE -> BuildCTableJoinQueryCondition
    AGG -> AttributeCreator_2
BuildCTableJoinQueryCondition
    NOMODEFIELDS = @Value(NoModeFieldsAux)
    TMODE_NAME = @Value(TMODE_Name)
    _FIELDNAME = @Value(_FieldName)
    -> AttributeCreator_7
Note: Build MODE subquery and JOIN criteria
AttributeCreator_7
    ATTR_TABLE:
      SET_TO __SQLFieldNames = FME_CONDITIONAL:DEFAULT_VALUE''BOOL_OP;OR;COMPOSITE_TEST;1;TEST join_cond ATTRIBUTE_HAS_A_VALUE _FME_BLANK_STRING_'LEFT JOIN   jedi_cubes.`@Value(TMODE_Name)_C_@Value(_FieldName)`   ON
             @Value(GridNumCond)
            @Value(join_cond)'FME_NUM_CONDITIONS2___
      SET_TO CachedModeSubQueryCTable = FME_CONDITIONAL:DEFAULT_VALUE'drop table if exists jedi_cubes.`@Value(TMODE_Name)_C_@Value(_FieldName)`;
        SELECT
                @Value(_FieldName)
                FROM
        (SELECT
                @Value(_FieldName),
                row_number()
         OVER ( ORDER BY count(@Value(_FieldName)) DESC ) as MODE
         FROM jedi_cubes.`@Value(TMODE_Name)_@Value(_FieldName)`
         GROUP BY
                @Value(_FieldName))
        WHERE MODE = 1'BOOL_OP;OR;COMPOSITE_TEST;1;TEST NoModeFields ATTRIBUTE_HAS_A_VALUE _FME_BLANK_STRING_'drop table if exists jedi_cubes.`@Value(TMODE_Name)_C_@Value(_FieldName)`;
        SELECT
                @ReplaceString(@ReplaceString(@Value(NoModeFieldsAux),`@Value(_TableName)`.,""),"jedi_cubes.",""),
                @Value(_FieldName)
                FROM
        (SELECT

                @ReplaceString(@ReplaceString(@Value(NoModeFieldsAux),`@Value(_TableName)`.,""),"jedi_cubes.",""),
                @Value(_FieldName),
                row_number()
         OVER (PARTITION BY @ReplaceString(@ReplaceString(@Value(NoModeFieldsAux),`@Value(_TableName)`.,""),"jedi_cubes.","") ORDER BY count(@Value(_FieldName)) DESC ) as MODE
         FROM jedi_cubes.`@Value(TMODE_Name)_@Value(_FieldName)`
         GROUP BY
               @ReplaceString(@ReplaceString(@Value(NoModeFieldsAux),`@Value(_TableName)`.,""),"jedi_cubes.",""),
                @Value(_FieldName))
        WHERE MODE = 1'FME_NUM_CONDITIONS2___
    -> AttributeCreator_2
Note: Add something after field
AttributeCreator_2
    ATTR_TABLE = SET_TO __SQLFieldNames = FME_CONDITIONAL:DEFAULT_VALUE'_FME_NO_OP_'BOOL_OP;OR;COMPOSITE_TEST;<Unused>;TEST @Value(_AddAfterField) ATTRIBUTE_HAS_VALUE _FME_BLANK_STRING_'@Value(__SQLFieldNames) @Value(_AddAfterField)'FME_NUM_CONDITIONS2___
    -> StringPadder
Note: Add indents to make the / TSQL look nice
StringPadder
    BLANK_ATTRIBUTE = Yes
    PADCHAR = "\t"
    SIDE = Left
    SRC_ATTRS = __SQLFieldNames
    WIDTH = @Value(_TotalIndents)+@StringLength(@Value(__SQLFieldNames))
    -> Sorter
    <REJECTED> -> Aggregator_2
Note: Make field snippeds unqiue
Aggregator_2 [off]
    ACCUM_ATTRS_NAME = Use Attributes From One Feature
    AGGREGATE_TYPE = Homogeneous Collection (If Possible)
    MODE = Geometry - Assemble One Level
    ORDERED = No
    SEP = ,
    AGGREGATE -> Sorter
Note: Make sure we order / as they came in
Sorter
    SORT_PARM = _count NUMERIC ASCENDING
    SORTED -> AttributeRemover_2
    SORTED -> AttributeKeeper
AttributeRemover_2
    REMOVE_ATTRS = CachedModeSubQueryCTable
    -> Aggregator
Note: Combine them all together
Aggregator
    ACCUM_ATTRS_NAME = Use Attributes From One Feature
    AGGREGATE_TYPE = Homogeneous Collection (If Possible)
    CONCAT_ATTRS = __SQLFieldNames join_cond
    MODE = Geometry - Assemble One Level
    ORDERED = No
    SEP = " "
    AGGREGATE -> FeatureMerger_2 [REQUESTOR]
AttributeKeeper
    CREATE_BULK_MODE_FEATURES = NO
    KEEP_ATTRS = __SQLFieldNames,CachedModeSubQueryCTable
    -> Aggregator_3
Note: Build TMODE_C combined query
Aggregator_3
    ACCUM_ATTRS_NAME = Use Attributes From One Feature
    AGGREGATE_TYPE = Homogeneous Collection (If Possible)
    CONCAT_ATTRS = CachedModeSubQueryCTable
    MODE = Geometry - Assemble One Level
    ORDERED = No
    SEP = ","
    AGGREGATE -> FeatureMerger_2 [SUPPLIER]
FeatureMerger_2
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> PythonCaller
Note: Set to users attribute
PythonCaller
    NEW_ATTRIBUTES = ModeFields
    PYTHONSOURCE:
      import fme
      import re
      import fmeobjects

      # Template Function interface:
      # When using this function, make sure its name is set as the value of
      # the 'Class or Function to Process Features' transformer parameter
      def processFeature(feature):
          pass

      # Template Class Interface:
      # When using this class, make sure its name is set as the value of
      # the 'Class or Function to Process Features' transformer parameter
      class FeatureProcessor(object):
          def __init__(self):
              pass
          def input(self,feature):
              #
              # Move the new value into the target attribute user has chosen.
              #
              TargetAttribute = feature.getAttribute("_TargetAttribute")
              SQLFieldNames = feature.getAttribute("__SQLFieldNames")

              ModeFields = feature.getAttribute('CachedModeSubQueryCTable')
              ModeFields = re.sub(r"[\n\t\s]*", "", ModeFields)

              if (SQLFieldNames.startswith(',')):
                  SQLFieldNames= SQLFieldNames[1:]

              if (SQLFieldNames.endswith(',')):
                  SQLFieldNames= SQLFieldNames[:-1]

              feature.setAttribute(TargetAttribute,SQLFieldNames)
              feature.setAttribute("ModeFields",ModeFields)
              self.pyoutput(feature)
          def close(self):
              pass
    PYTHONSYMBOL = FeatureProcessor
    -> AttributeCreator_4
Note: Build LEFT JOIN clause
AttributeCreator_4
    ATTR_TABLE = SET_TO ModeSubQueryCube = @Value(__SQLFieldNames)
    -> AttributeRemover
AttributeRemover
    REMOVE_ATTRS = __SQLFieldNames,_AddAfterField,_TableName,_count,_AggregateFunction,_FieldName,_TargetAttribute,T1Fields,_TotalIndents,TAFields,_DatabaseOwner,NoModeFieldsAux
    -> FeatureMerger [SUPPLIER]
Note: Remap new value to all values
FeatureMerger
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> Output_2 (output)
Output_2 (output)

FME custom transformer CreateTableAParts

Parameters:
- ADDGRIDNUMSCALE =
- CUBEID =
- F_TABLENAMEA =
- F_TABLENAMEHIGHTOLOW =
- MODEFIELDS =
- MODESUBQUERY =
- NOMODEFIELDS =
- NUMGROUPTABLEA =
- SQL_NOMODE =
- _AGGREGATEFUNCTION =
- _FIELDALIAS =
- _FIELDNAME =

Input (input)
    -> FeatureJoiner_4 [LEFT]
    -> AllFieldsCreator
FeatureJoiner_4
    ATTR_CONFLICT_RES = Use Left
    GEOMETRY_HANDLING = Use Left
    JOIN_KEYS = CubeId CubeId AUTO
    JOIN_MODE = Inner
    JOINED -> AttributeKeeper_8
    JOINED -> AttributeKeeper_7
    JOINED -> FeatureJoiner_3 [LEFT]
FeatureJoiner
    ATTR_CONFLICT_RES = Use Left
    GEOMETRY_HANDLING = Use Left
    JOIN_KEYS = F_TableNameA F_TableNameA AUTO
    JOIN_MODE = Inner
    JOINED -> FeatureJoiner_2 [LEFT]
    JOINED -> StringConcatenator
    UNJOINED_RIGHT -> F_TableA
FeatureJoiner_2
    ATTR_CONFLICT_RES = Use Right
    GEOMETRY_HANDLING = Use Left
    JOIN_KEYS = F_TableNameA F_TableNameA AUTO
    JOIN_MODE = Left
    JOINED -> AttributeKeeper_2
AttributeKeeper_2
    CREATE_BULK_MODE_FEATURES = NO
    KEEP_ATTRS = F_TableTSQLA_Part,NumGroupTableA,F_TableTSQL_A,F_TableNameA
    -> Aggregator_2
Aggregator_2
    ACCUM_ATTRS_NAME = Use Attributes From One Feature
    AGGREGATE_TYPE = Homogeneous Collection (If Possible)
    CONCAT_ATTRS = F_TableTSQLA_Part
    MODE = Geometry - Assemble One Level
    SEP = ","
    AGGREGATE -> FeatureJoiner_3 [RIGHT]
FeatureJoiner_3
    ATTR_CONFLICT_RES = Use Right
    GEOMETRY_HANDLING = Use Left
    JOIN_KEYS = F_TableNameA F_TableNameA AUTO
    JOIN_MODE = Left
    JOINED -> Output (output)
Output (output)

Bookmark: Build All Fields Attribute
AllFieldsCreator: AttributeCreator
    ATTR_TABLE = SET_TO AllTableFields = FME_CONDITIONAL:DEFAULT_VALUE'jedi_cubes.@Value(F_TableNameHighToLow).@Value(_FieldAlias)'BOOL_OP;AND;COMPOSITE_TEST;1 AND 2;TEST _AggregateFunction ATTRIBUTE_HAS_A_VALUE _FME_BLANK_STRING_;TEST @Value(_AggregateFunction) = MODE' jedi_cubes.`@Value(F_TableNameA)_Part@Value(NumGroupTableA)`.@Value(_FieldAlias)'BOOL_OP;AND;COMPOSITE_TEST;1 AND 2;TEST _AggregateFunction ATTRIBUTE_HAS_A_VALUE _FME_BLANK_STRING_;TEST @Value(_AggregateFunction) != MODE'@Value(_AggregateFunction)(jedi_cubes.@Value(F_TableNameHighToLow).@Value(_FieldAlias) ) as @Value(_FieldAlias)'FME_NUM_CONDITIONS3___
    -> Aggregator_3
Aggregator_3
    ACCUM_ATTRS_NAME = Use Attributes From One Feature
    AGGREGATE_TYPE = Homogeneous Collection (If Possible)
    CONCAT_ATTRS = AllTableFields
    MODE = Geometry - Assemble One Level
    SEP = ",\n"
    AGGREGATE -> AllTableFieldsGroupBy
AllTableFieldsGroupBy: AttributeCreator
    ATTR_TABLE = SET_TO AllTableFieldsGroupped = @Value(AllTableFields)
    -> ReplaceTMode_And_AGG
ReplaceTMode_And_AGG: StringReplacer
    CASE = NO
    FIND_TEXT = (SUM|COUNT|AVG|MAX|MIN|STDEV|STDEVP|VAR|VARP|MODE)\([`.+`,a-z,\,A-Z,_, ,\.,0-9,\-,\(,\),\)]{1,}
    NO_MATCH = _FME_NO_OP_
    REGEXP = YES
    SRC_ATTRS = AllTableFieldsGroupped
    -> FeatureJoiner_4 [RIGHT]

Bookmark: Create F_Table_A_Parts queries, and left joins for the F_Table_A query
AttributeKeeper_7
    CREATE_BULK_MODE_FEATURES = NO
    KEEP_ATTRS = F_TableNameA,AddGridNumScale,F_TableNameHighToLow,ModeSubQuery,SQL_NoMode,NoModeFields,NumGroupTableA,ModeFields,AllTableFields,AllTableFieldsGroupped
    -> DuplicateFilter_3
DuplicateFilter_3
    INPUT_ORDERED_CHOICE = No
    KEYATTR = NumGroupTableA
    UNIQUE -> FilterModes
FilterModes: Tester
    BOOL_OP = OR
    COMPOSITE_TEST = 1
    TEST_CLAUSE = TEST @Value(NumGroupTableA) >= 0
    TEST_MODE = TEST
    PASSED -> AttributeCreator_3
AttributeCreator_3
    ATTR_TABLE = SET_TO SQL_NoModeGroupped = @Value(NoModeFields)
    -> DeleteAggFields
DeleteAggFields: StringReplacer
    CASE = NO
    FIND_TEXT = (SUM|COUNT|AVG|MAX|MIN|STDEV|STDEVP|VAR|VARP|MODE)\([`.+`,a-z,\,A-Z,_, ,\.,0-9,\-,\(,\),\)]{1,}
    NO_MATCH = _FME_NO_OP_
    REGEXP = YES
    SRC_ATTRS = SQL_NoModeGroupped
    -> RemoveWhiteLines
RemoveWhiteLines: PythonCaller
    PYTHONSOURCE:
      import fme
      import fmeobjects
      import re
      # Template Function interface:
      # When using this function, make sure its name is set as the value of
      # the 'Class or Function to Process Features' transformer parameter
      def processFeature(feature):
          pass

      # Template Class Interface:
      # When using this class, make sure its name is set as the value of
      # the 'Class or Function to Process Features' transformer parameter
      class FeatureProcessor(object):
          def __init__(self):
              pass
          def input(self,feature):
              sqlNoMode= feature.getAttribute('SQL_NoModeGroupped')
              if (sqlNoMode!=""):
                  sqlNoMode = "\n".join([ll.rstrip() for ll in sqlNoMode.splitlines() if ll.strip()])
                  sqlNoMode = sqlNoMode.strip()
                  if (sqlNoMode[-1] ==","):
                      sqlNoMode = sqlNoMode[:-1]

              feature.setAttribute('SQL_NoModeGroupped',sqlNoMode)


              self.pyoutput(feature)
          def close(self):
              pass
    PYTHONSYMBOL = FeatureProcessor
    -> AttributeCreator_2
AttributeCreator_2
    ATTR_TABLE:
      SET_TO SQL_Partition = @ReplaceString(
        @Value(SQL_NoModeGroupped),"jedi_cubes.@Value(F_TableNameHighToLow).","")
    -> AttributeCreator_5
AttributeCreator_5
    ATTR_TABLE:
      SET_TO F_TableTSQLA_Part = FME_CONDITIONAL:DEFAULT_VALUE'drop table if exists jedi_cubes.`@Value(F_TableNameA)_Part@Value(NumGroupTableA)`;
        SELECT *,
        row_number()  OVER (PARTITION BY GridNum10Km, GridNum,@Value(SQL_Partition) ORDER BY areaHa)  as numrow
        FROM (
        SELECT
                jedi_cubes.`@Value(F_TableNameHighToLow)`.`GridNum10km`,
               @Value(AddGridNumScale) as GridNum,
               jedi_cubes.`@Value(F_TableNameHighToLow)`.`AreaHa`,
               @Value(SQL_NoModeGroupped),
               @Value(ModeFields)
        FROM jedi_cubes.`@Value(F_TableNameHighToLow)` @Value(ModeSubQuery)
        )

          'BOOL_OP;OR;COMPOSITE_TEST;1;TEST SQL_NoModeGroupped ATTRIBUTE_IS_EMPTY _FME_BLANK_STRING_'drop table if exists jedi_cubes.`@Value(F_TableNameA)_Part@Value(NumGroupTableA)`;
        SELECT *,
        row_number()  OVER (PARTITION BY GridNum10Km, GridNum ORDER BY areaHa)  as numrow
        FROM (

        SELECT
                jedi_cubes.`@Value(F_TableNameHighToLow)`.`GridNum10km`,
               @Value(AddGridNumScale) as GridNum,
               jedi_cubes.`@Value(F_TableNameHighToLow)`.`AreaHa`,
                @Value(ModeFields)
        FROM jedi_cubes.`@Value(F_TableNameHighToLow)` @Value(ModeSubQuery)
        )'FME_NUM_CONDITIONS2___
      SET_TO F_TableTSQLA_Left_Join_Gridnums_Part =     LEFT JOIN jedi_cubes.`@Value(F_TableNameA)_Part@Value(NumGroupTableA)`
                ON       jedi_cubes.`@Value(F_TableNameA)_Part@Value(NumGroupTableA)`.`GridNum` = @Value(AddGridNumScale)
            AND
                jedi_cubes.`@Value(F_TableNameA)_Part@Value(NumGroupTableA)`.`GridNum10km` = jedi_cubes.`@Value(F_TableNameHighToLow)`.`GridNum10km`
            AND
                jedi_cubes.`@Value(F_TableNameA)_Part@Value(NumGroupTableA)`.`numrow` = jedi_cubes.`@Value(F_TableNameHighToLow)`.`numrow`
    -> AttributeRemover
AttributeRemover
    REMOVE_ATTRS = SQL_NoModeGroupped
    -> FeatureJoiner [LEFT]

Bookmark: Get the fields with no agg function to build the joins for F_Table_A query
AttributeKeeper_8
    CREATE_BULK_MODE_FEATURES = NO
    KEEP_ATTRS = NoModeFields,F_TableNameA,AllTableFields,AllTableFieldsGroupped,F_TableNameHighToLow,AddGridNumScale
    -> DuplicateFilter_4
DuplicateFilter_4
    INPUT_ORDERED_CHOICE = No
    KEYATTR = NoModeFields
    UNIQUE -> AttributeSplitter
AttributeSplitter
    ATTR_NAME = NoModeFields
    DELIMITER = ,
    DROP_EMPTY_PARTS = No
    LIST_NAME = _list
    TRIM_OPTION = Both
    -> ListExploder
ListExploder
    ATTR_ACCUM_MODE = Merge List Attributes
    ATTR_CONFLICT_RES = Use List Attribute Values
    INDEX_ATTR = _element_index
    LIST_ATTR = _list{}
    ELEMENTS -> AttributeSplitter_2
AttributeSplitter_2
    ATTR_NAME = _list
    DELIMITER = .
    DROP_EMPTY_PARTS = No
    LIST_NAME = _list2
    TRIM_OPTION = Both
    -> TestFilter
TestFilter
    DEFAULT_VALUE = <UNFILTERED>
    TEST_LIST = "BOOL_OP,OR,COMPOSITE_TEST,""""""1"""""",TEST_CLAUSE,TEST NoModeFields ATTRIBUTE_HAS_A_VALUE """,NoModeFields ATTRIBUTE_HAS_A_VALUE
    NoModeFields ATTRIBUTE_HAS_A_VALUE -> AttributeCreator_23
    <UNFILTERED> -> AttributeCreator_4
Aggregator
    ACCUM_ATTRS_NAME = Use Attributes From One Feature
    AGGREGATE_TYPE = Homogeneous Collection (If Possible)
    CONCAT_ATTRS = F_TableTSQLA_Left_Join_NoMode_Part
    MODE = Geometry - Assemble One Level
    SEP = "\n"
    AGGREGATE -> FeatureJoiner [RIGHT]

Bookmark: Check if there are no AGG or MODE fields
AttributeCreator_23
    ATTR_TABLE = SET_TO F_TableTSQLA_Left_Join_NoMode_Part =     AND  CASE WHEN isnull(jedi_cubes.`@Value(F_TableNameA)_PartNUMGROUPREPLACE`.@Value(_list2{2})) then '#*#' else CAST(jedi_cubes.`@Value(F_TableNameA)_PartNUMGROUPREPLACE`.@Value(_list2{2}) as string) END= CASE WHEN isnull(@Value(_list)) then '#*#' else CAST(@Value(_list) as string) END
    -> Aggregator
AttributeCreator_4
    ATTR_TABLE = SET_TO F_TableTSQLA_Left_Join_NoMode_Part
    -> Aggregator

Bookmark: F_TableA no MODEs
Note: F_Table_A when there is no MODE. Rename HighToLow to F_TAbleA
F_TableA: AttributeCreator
    ATTR_TABLE:
      SET_TO F_TableTSQL_A = drop table if exists jedi_cubes.`@Value(F_TableNameA)`;
        ALTER TABLE jedi_cubes.`@Value(F_TableNameHighToLow)` RENAME TO jedi_cubes.`@Value(F_TableNameA)`
    -> FeatureJoiner_3 [RIGHT]

Bookmark: Create F_Table_A query
StringConcatenator
    ACTION = Create New Attribute
    PARM_LINE:
      fme_basicstring:44%1%42:@Value(F_TableTSQLA_Left_Join_Gridnums_Part)
      @Value(F_TableTSQLA_Left_Join_NoMode_Part)
    VAL_ATTR = F_TableTSQLA_Left_Join_Part
    -> StringReplacer
StringReplacer
    CASE = NO
    FIND_TEXT = NUMGROUPREPLACE
    NO_MATCH = _FME_NO_OP_
    REGEXP = NO
    REPLACE_TEXT = @Value(NumGroupTableA)
    SRC_ATTRS = F_TableTSQLA_Left_Join_Part
    -> Aggregator_6
Aggregator_6
    ACCUM_ATTRS_NAME = Use Attributes From One Feature
    AGGREGATE_TYPE = Homogeneous Collection (If Possible)
    CONCAT_ATTRS = F_TableTSQLA_Left_Join_Part
    MODE = Geometry - Assemble One Level
    SEP = "\n"
    AGGREGATE -> AttributeCreator
AttributeCreator
    ATTR_TABLE:
      SET_TO F_TableTSQL_A = drop table if exists jedi_cubes.`@Value(F_TableNameA)`;
        SELECT
                jedi_cubes.`@Value(F_TableNameHighToLow)`.`GridNum10km`,
               @Value(AddGridNumScale) as GridNum,
               @Value(AllTableFields),
                 Sum(( jedi_cubes.@Value(F_TableNameHighToLow).AreaHa )) as AreaHa

        FROM jedi_cubes.`@Value(F_TableNameHighToLow)` @Value(F_TableTSQLA_Left_Join_Part)
        GROUP BY
                jedi_cubes.`@Value(F_TableNameHighToLow)`.`GridNum10km`,
               @Value(AddGridNumScale),
               @Value(AllTableFieldsGroupped)
    -> AttributeKeeper
AttributeKeeper
    CREATE_BULK_MODE_FEATURES = NO
    KEEP_ATTRS = F_TableNameA,F_TableTSQL_A
    -> FeatureJoiner_2 [RIGHT]

FME custom transformer DatabricksAPICaller
Custom Transformer to call Databricks API

Parameters:
- COMMAND =
- DOMAIN =
- JOBID =
- METHOD =
- PARAMETER =
- RUNID =
- TOKEN =

DatabrickAPICallerInput (input)
    -> ParameterFetcher
ParameterFetcher
    ATTR_LIST = _TOKEN $(TOKEN) _DOMAIN $(DOMAIN)
    -> CallDatabricksJob
Note: Call databricks API
CallDatabricksJob: PythonCaller
    NEW_ATTRIBUTES = RunId status result num_records has_overlaps error noError cmd fields
    PYTHONSOURCE:
      import fme
      import fmeobjects
      import json
      import base64
      import requests
      import re


      # Template Function interface:
      # When using this function, make sure its name is set as the value of
      # the 'Class or Function to Process Features' transformer parameter
      def dbfs_rpc(action, body,TOKEN,BASE_URL):
        """ A helper function to make the API request, request/response is encoded/decoded as JSON """
        response = requests.post(
          BASE_URL + action,
          headers={"Authorization":"Bearer " +str(TOKEN) },
          json=body
        )
        return response.json()

      def dbfs_get_rpc(action, body,TOKEN,BASE_URL):
        """ A helper function to make the API request, request/response is encoded/decoded as JSON """
        response = requests.get(
          BASE_URL + action,
          headers={"Authorization":"Bearer " + str(TOKEN) },
          params= body
        )
        return response.json()



      def processFeature(feature):
          pass

      # Template Class Interface:
      # When using this class, make sure its name is set as the value of
      # the 'Class or Function to Process Features' transformer parameter
      class FeatureProcessor(object):
          def __init__(self):
              pass
          def input(self,feature):
              runId= 0
              status=""
              result=""
              num_records =0
              has_overlaps =0
              error= ""
              noError=0
              cmd =0
              fields=""
              try:

                  raw_data = {}
                  if feature.getAttribute('RunId'):
                      raw_data['run_id']= str(feature.getAttribute('RunId'))
                  if feature.getAttribute('JobId'):
                      raw_data['job_id']= feature.getAttribute('JobId')

                  if feature.getAttribute('Parameter'):
                      paramTxt = "{" + str(feature.getAttribute('Parameter')) + "}"
                      formatedParam = paramTxt.replace("\n"," ").replace("\t", " ").replace("  "," ")
                      parameter = json.loads(formatedParam)
                      raw_data['notebook_params'] = parameter

                  DOMAIN = str(feature.getAttribute('_DOMAIN'))
                  TOKEN = str(feature.getAttribute('_TOKEN'))
                  BASE_URL = 'https://%s/api/2.0/jobs/' % (DOMAIN)


                  if feature.getAttribute('Method') == 'POST':
                      handle = dbfs_rpc(feature.getAttribute('Command'), raw_data,TOKEN, BASE_URL)
                  else:
                      handle = dbfs_get_rpc(feature.getAttribute('Command'), raw_data,TOKEN, BASE_URL)
                  noError=0

                  if ('run_id' in handle):
                      runId= handle['run_id']
                  else:
                      runId= str(feature.getAttribute('RunId'))

                  if 'metadata' in handle:
                      if 'state' in handle['metadata']:
                          if 'life_cycle_state' in handle['metadata']['state']:
                              status = handle['metadata']['state']['life_cycle_state']
                          if 'result_state' in handle['metadata']['state']:
                              result = handle['metadata']['state']['result_state']

                      if status == 'TERMINATED' : # and 'notebook_output' in handle:
                          if 'result' in  handle['notebook_output']:
                              output = handle['notebook_output']['result'].replace('\n', ' ').replace('\r', '').replace('\t', '').replace("  ","")
                              print("******")
                              print(output)
                              print("****")
                              res = json.loads(output)
                              print(res)
                              noError = res['status']
                              cmd = res['cmd']
                              error = res['error']
                              if 'num_records' in res:
                                  num_records = res['num_records']
                              if 'has_overlaps' in res:
                                  has_overlaps = res['has_overlaps']
                              if 'fields' in res:
                                  fields = str(res['fields'])
                                  fields = fields.replace("'fieldname': '", '"fieldname": "')
                                  fields = fields.replace("', 'grouporder':",'", "grouporder":')
                                  fields = fields.replace("'fieldValue': '",'"fieldValue": "')
                                  fields = fields.replace("', 'TotalRecord':",'", "TotalRecord":')
                                  fields = fields.replace("'fieldValue'",'"fieldValue"')
                                  fields = fields.replace("'TotalRecord'",'"TotalRecord"')

              except Exception as err:
                  print("DATABRICKS ERRROR")
                  print("error:" + str(err))
                  feature.setAttribute("RunId",0)
                  feature.setAttribute("error",str(err))
                  feature.setAttribute("noError",0)

              feature.setAttribute("RunId",runId)
              feature.setAttribute("status",status)
              feature.setAttribute("result",result)
              feature.setAttribute("num_records",num_records)
              feature.setAttribute("has_overlaps",has_overlaps)
              feature.setAttribute("error",error)
              feature.setAttribute("noError",noError)
              feature.setAttribute("cmd",cmd)
              feature.setAttribute("fields",fields)
              self.pyoutput(feature)

          def close(self):
              pass
    PYTHONSYMBOL = FeatureProcessor
    -> CallDatabricksJob_Output (output)
CallDatabricksJob_Output (output)

FME custom transformer GetFromTableName

Parameters:
- DIMGRIDSPACING =
- DIMGRIDTYPENAME =
- F_TABLENAME =
- GRIDTYPENAME =
- GRIDTYPETARGET =
- G_TABLENAME =
- _SQLFIELDSHIGHTOLOW =
- _SQL_GROUPBY_FIELDS_HIGHTOLOW =

Input (input)
    -> Aggregator
Note: Aggregate on Grid types
Aggregator
    ACCUM_ATTRS_NAME = Use Attributes From One Feature
    AGGREGATE_TYPE = Homogeneous Collection (If Possible)
    GROUP_BY = _SQLFieldsHighToLow DimGridTypeName
    MODE = Geometry - Assemble One Level
    ORDERED = No
    SEP = ,
    AGGREGATE -> Sorter
Sorter
    SORT_PARM = DimGridSpacing NUMERIC ASCENDING
    SORTED -> Counter
Counter
    CNT_ATTR = NumScales
    DOMAIN = counter
    SCOPE = Local
    START = 0
    -> StatisticsCalculator
Note: Find minimum grid spacing
StatisticsCalculator
    COMPUTE_HISTOGRAM = NO
    COUNT_ATTR = _TotalGridTypes
    MIN_ATTR = _minDimGridSpacing
    PREPEND_ATTR_NAME_CHOICE = For multiple results only
    STATS_ATTRS = DimGridSpacing
    COMPLETE -> TestFilter_2
    COMPLETE -> AttributeCreator_8
Note: Create Table name scale dependent / _FromHighToLow
AttributeCreator_8
    ATTR_TABLE = SET_TO _FromHighToLow = FME_CONDITIONAL:DEFAULT_VALUE'_FME_NO_OP_'BOOL_OP;OR;COMPOSITE_TEST;1;TEST @Value(_minDimGridSpacing) = 10'@Value(F_TableName)_10m'BOOL_OP;OR;COMPOSITE_TEST;<Unused>;TEST @Value(_minDimGridSpacing) = 100'@Value(F_TableName)_100m'BOOL_OP;OR;COMPOSITE_TEST;<Unused>;TEST @Value(_minDimGridSpacing) = 1000'@Value(F_TableName)_1km'BOOL_OP;OR;COMPOSITE_TEST;<Unused>;TEST @Value(_minDimGridSpacing) = 10000'@Value(F_TableName)_10km'FME_NUM_CONDITIONS5___
    -> TestFilter
    -> Aggregator_2
    -> FeatureJoiner [LEFT]
Aggregator_2
    ACCUM_ATTRS_NAME = Merge Incoming Attributes
    AGGREGATE_TYPE = Homogeneous Collection (If Possible)
    CONCAT_ATTRS = DimGridTypeName
    MODE = Geometry - Assemble One Level
    SEP = ,
    AGGREGATE -> AttributeCreator_4
AttributeCreator_4
    ATTR_TABLE = SET_TO AllScales = @Value(DimGridTypeName)
    -> AttributeKeeper
AttributeKeeper
    CREATE_BULK_MODE_FEATURES = NO
    KEEP_ATTRS = AllScales,_TotalGridTypes
    -> FeatureJoiner [RIGHT]
FeatureJoiner
    ATTR_CONFLICT_RES = Use Left
    GEOMETRY_HANDLING = Use Left
    JOIN_KEYS = _TotalGridTypes _TotalGridTypes AUTO
    JOIN_MODE = Inner
    JOINED -> PreviousScale_2
Note: Set previous scales
PreviousScale_2: AttributeCreator
    ATTR_TABLE:
      SET_TO PreviousScale = FME_CONDITIONAL:DEFAULT_VALUE'_FME_NO_OP_'BOOL_OP;OR;COMPOSITE_TEST;1;TEST @Value(DimGridSpacing) = 10'1m'BOOL_OP;OR;COMPOSITE_TEST;1;TEST @Value(DimGridSpacing) = 100'10m'BOOL_OP;AND;COMPOSITE_TEST;1 AND 2;TEST @Value(DimGridSpacing) = 1000;CASE_INSENSITIVE_TEST @Value(AllScales) CONTAINS 100m'100m'BOOL_OP;AND;COMPOSITE_TEST;1 AND 2;TEST @Value(DimGridSpacing) = 1000;CASE_INSENSITIVE_TEST @Value(AllScales) CONTAINS 10m'10m'BOOL_OP;AND;COMPOSITE_TEST;1 AND 2;TEST @Value(DimGridSpacing) = 10000;CASE_INSENSITIVE_TEST @Value(AllScales) CONTAINS 1km'1km'BOOL_OP;AND;COMPOSITE_TEST;1 AND 2;TEST @Value(DimGridSpacing) = 10000;CASE_INSENSITIVE_TEST @Value(AllScales) CONTAINS 100m'100m'BOOL_OP;AND;COMPOSITE_TEST;1 AND 2;TEST @Value(DimGridSpacing) = 10000;CASE_INSENSITIVE_TEST @Value(AllScales) CONTAINS 10m'10m'FME_NUM_CONDITIONS8___
      SET_TO RemoveFromQuery = FME_CONDITIONAL:DEFAULT_VALUE'_FME_NO_OP_'BOOL_OP;OR;COMPOSITE_TEST;1;TEST @Value(DimGridSpacing) = 10'100m,1km,10km'BOOL_OP;OR;COMPOSITE_TEST;1;TEST @Value(DimGridSpacing) = 100'1km,10km'BOOL_OP;OR;COMPOSITE_TEST;1;TEST @Value(DimGridSpacing) = 1000'10km'FME_NUM_CONDITIONS4___
      SET_TO NextScale = FME_CONDITIONAL:DEFAULT_VALUE'10km'BOOL_OP;AND;COMPOSITE_TEST;1 AND 2;TEST @Value(DimGridSpacing) = 10;CASE_INSENSITIVE_TEST @Value(AllScales) CONTAINS 100m'100m'BOOL_OP;AND;COMPOSITE_TEST;1 AND 2;TEST @Value(DimGridSpacing) = 10;CASE_INSENSITIVE_TEST @Value(AllScales) CONTAINS 1km'1km'BOOL_OP;AND;COMPOSITE_TEST;1 AND 2;TEST @Value(DimGridSpacing) = 10;CASE_INSENSITIVE_TEST @Value(AllScales) CONTAINS 10km'10km'BOOL_OP;AND;COMPOSITE_TEST;1 AND 2;TEST @Value(DimGridSpacing) = 100;CASE_INSENSITIVE_TEST @Value(AllScales) CONTAINS 1km'1km'FME_NUM_CONDITIONS5___
    -> AttributeSplitter
GridNumTranslator: AttributeCreator
    ATTR_TABLE:
      SET_TO ConvertGridNum = FME_CONDITIONAL:DEFAULT_VALUE''BOOL_OP;OR;COMPOSITE_TEST;1;TEST @Value(DimGridSpacing) = 10'-256 'BOOL_OP;OR;COMPOSITE_TEST;1;TEST @Value(DimGridSpacing) = 100'-65536'BOOL_OP;OR;COMPOSITE_TEST;1;TEST @Value(DimGridSpacing) = 1000'-16777216'BOOL_OP;OR;COMPOSITE_TEST;1;TEST @Value(DimGridSpacing) = 10000'-4294967296'FME_NUM_CONDITIONS5___
      SET_TO MinScaleName = FME_CONDITIONAL:DEFAULT_VALUE''BOOL_OP;OR;COMPOSITE_TEST;1;TEST @Value(_minDimGridSpacing) = 10'10m'BOOL_OP;OR;COMPOSITE_TEST;1;TEST @Value(_minDimGridSpacing) = 100'100m'BOOL_OP;OR;COMPOSITE_TEST;1;TEST @Value(_minDimGridSpacing) = 1000'1km'BOOL_OP;OR;COMPOSITE_TEST;1;TEST @Value(_minDimGridSpacing) = 10000'10km'FME_NUM_CONDITIONS5___
    -> FirstScale
FirstScale: TestFilter
    DEFAULT_VALUE = NULL
    TEST_LIST:
      "BOOL_OP,AND,COMPOSITE_TEST,""""""1 AND 2"""""",TEST_CLAUSE,TEST @Value(NumScales) = 0
      TEST @Value(_TotalGridTypes) = 1",SingleScale,"BOOL_OP,OR,COMPOSITE_TEST,""""""1"""""",TEST_CLAUSE,TEST @Value(NumScales) = @Evaluate(@Value(_TotalGridTypes)-1)",Last,"BOOL_OP,OR,COMPOSITE_TEST,""""""1"""""",TEST_CLAUSE,TEST @Value(NumScales) = 1",FirstScale,"BOOL_OP,OR,COMPOSITE_TEST,""""""1"""""",TEST_CLAUSE,TEST @Value(NumScales) > 0",Other
    SingleScale -> AttributeCreator_5
    Last -> TestFilter_3
    FirstScale -> AttributeCreator
    Other -> AttributeCreator_3
AttributeCreator_5
    ATTR_TABLE:
      SET_TO F_TableNameHighToLow = @Value(F_TableName)_HighToLow
      SET_TO GridNumScale = GridNum
      SET_TO GridTypeTarget = FME_CONDITIONAL:DEFAULT_VALUE'_FME_NO_OP_'BOOL_OP;OR;COMPOSITE_TEST;1;TEST @Value(GridTypeName) = 10m'10'BOOL_OP;OR;COMPOSITE_TEST;1;TEST @Value(GridTypeName) = 100m'100'BOOL_OP;OR;COMPOSITE_TEST;1;TEST @Value(GridTypeName) = 1km'1000'BOOL_OP;OR;COMPOSITE_TEST;1;TEST @Value(GridTypeName) = 10km'10000'FME_NUM_CONDITIONS5___
    -> Output (output)
AttributeCreator
    ATTR_TABLE:
      SET_TO F_TableNameHighToLow = FME_CONDITIONAL:DEFAULT_VALUE'@Value(F_TableName)_HighToLow_@Value(DimGridTypeName)'BOOL_OP;OR;COMPOSITE_TEST;1;TEST @Value(_TotalGridTypes) = 2'@Value(F_TableName)_HighToLow'FME_NUM_CONDITIONS2___
      SET_TO GridNumScale = FME_CONDITIONAL:DEFAULT_VALUE'GridNum@Value(NextScale)'BOOL_OP;OR;COMPOSITE_TEST;1;CASE_INSENSITIVE_TEST @Value(NextScale) = 10km'GridNum'FME_NUM_CONDITIONS2___
      SET_TO F_TableTSQLHighToLow = FME_CONDITIONAL:DEFAULT_VALUE'SELECT
            G.`GridNum10km`,
            G.`GridNum@Value(NextScale)` as @Value(GridNumScale),
            @Value(_SQLFieldsHighToLow),
          (sum(
             case
               when @Value(F_TableName)_@Value(PreviousScale).areaha is not null then @Value(F_TableName)_@Value(PreviousScale).areaha
               else @Value(F_TableName)_@Value(DimGridTypeName).areaha
             end
           )) as areaHa

        FROM
            jedi_cubes.@Value(G_TableName)_HighToLow_@Value(DimGridTypeName) as G
            LEFT JOIN
            jedi_cubes.@Value(F_TableName)_@Value(DimGridTypeName) on
            G.GridNum@Value(DimGridTypeName)=@Value(F_TableName)_@Value(DimGridTypeName).gridnum@Value(DimGridTypeName) and G.gridnum10km=@Value(F_TableName)_@Value(DimGridTypeName).gridnum10km
          LEFT JOIN
            jedi_cubes.@Value(F_TableName)_@Value(PreviousScale) ON G.gridnum@Value(DimGridTypeName)= jedi_cubes.@Value(F_TableName)_@Value(PreviousScale).GridNum@Value(DimGridTypeName)
                and G.gridnum10km=jedi_cubes.@Value(F_TableName)_@Value(PreviousScale).GridNum10km
        GROUP BY
             G.`GridNum10km`,
             G.`GridNum@Value(NextScale)`
        'BOOL_OP;OR;COMPOSITE_TEST;1;TEST @Value(_TotalGridTypes) = 2'SELECT
            G.`GridNum10km`,
            G.`GridNum@Value(GridTypeName)` as GridNum,
            @Value(_SQLFieldsHighToLow),
          (sum(
             case
               when @Value(F_TableName)_@Value(PreviousScale).areaha is not null then @Value(F_TableName)_@Value(PreviousScale).areaha
               else @Value(F_TableName)_@Value(DimGridTypeName).areaha
             end
           )) as areaHa

        FROM
            jedi_cubes.@Value(G_TableName)_HighToLow_@Value(DimGridTypeName) as G
            LEFT JOIN
            jedi_cubes.@Value(F_TableName)_@Value(DimGridTypeName) on
            G.GridNum@Value(DimGridTypeName)=@Value(F_TableName)_@Value(DimGridTypeName).gridnum@Value(DimGridTypeName) and G.gridnum10km=@Value(F_TableName)_@Value(DimGridTypeName).gridnum10km
          LEFT JOIN
            jedi_cubes.@Value(F_TableName)_@Value(PreviousScale) ON G.gridnum@Value(DimGridTypeName)= jedi_cubes.@Value(F_TableName)_@Value(PreviousScale).GridNum@Value(DimGridTypeName)
                and G.gridnum10km=jedi_cubes.@Value(F_TableName)_@Value(PreviousScale).GridNum10km
        GROUP BY
             G.`GridNum10km`,
             G.`GridNum@Value(GridTypeName)`
        'FME_NUM_CONDITIONS2___
    -> Output (output)
Note: Test if the previous scale is the min one, so it does't add the HighToLow in queries
TestFilter_3
    DEFAULT_VALUE = PrevNotMin
    TEST_LIST = "BOOL_OP,OR,COMPOSITE_TEST,""""""1"""""",TEST_CLAUSE,TEST @Value(PreviousScale) = @Value(MinScaleName)",PrevIsMin
    PrevIsMin -> AttributeCreator_6
    PrevNotMin -> AttributeCreator_2
AttributeCreator_6
    ATTR_TABLE:
      SET_TO F_TableNameHighToLow = @Value(F_TableName)_HighToLow
      SET_TO F_TableTSQLHighToLow = SELECT
            G.`GridNum10km`,
            G.`GridNum@Value(GridTypeName)` as GridNum,
            @Value(_SQLFieldsHighToLow),
          (sum(
             case
               when @Value(F_TableName)_@Value(PreviousScale).areaha is not null then @Value(F_TableName)_@Value(PreviousScale).areaha
               else @Value(F_TableName)_@Value(DimGridTypeName).areaha
             end
           )) as areaHa
        FROM
           jedi_cubes.@Value(G_TableName)_HighToLow_@Value(DimGridTypeName) as G
           LEFT JOIN
            jedi_cubes.@Value(F_TableName)_@Value(DimGridTypeName) on
            G.GridNum@Value(DimGridTypeName)=@Value(F_TableName)_@Value(DimGridTypeName).gridnum@Value(DimGridTypeName) and G.gridnum10km=@Value(F_TableName)_@Value(DimGridTypeName).gridnum10km
          LEFT JOIN
                jedi_cubes.@Value(F_TableName)_@Value(PreviousScale)  ON G.gridnum@Value(DimGridTypeName)=  jedi_cubes.@Value(F_TableName)_@Value(PreviousScale).GridNum@Value(DimGridTypeName)
                and G.gridnum10km=jedi_cubes.@Value(F_TableName)_@Value(PreviousScale).GridNum10km
        GROUP BY
            G.`GridNum10km`,
            G.`GridNum@Value(GridTypeName)`
      SET_TO Last = 1
    -> PythonCaller_2
PythonCaller_2
    PYTHONSOURCE:
      import fme
      import fmeobjects
      import re


      # Template Function interface:
      # When using this function, make sure its name is set as the value of
      # the 'Class or Function to Process Features' transformer parameter
      def processFeature(feature):
          pass

      # Template Class Interface:
      # When using this class, make sure its name is set as the value of
      # the 'Class or Function to Process Features' transformer parameter
      class FeatureProcessor(object):
          def __init__(self):
              pass
          def input(self,feature):
              scale = feature.getAttribute('DimGridTypeName')
              SQL = feature.getAttribute('F_TableTSQLHighToLow')
              tableName = feature.getAttribute('F_TableName')
              groupByFields = feature.getAttribute('_SQL_GroupBy_Fields_HighToLow')


              if (scale == "10m"):
                  SQL= re.sub(re.escape(tableName + "_1m"), tableName + "_1m", SQL, flags=re.IGNORECASE)
                  groupByFields= re.sub(re.escape(tableName + "_1m"), tableName + "_1m", groupByFields, flags=re.IGNORECASE)

              elif (scale == "100m"):
                  SQL= re.sub(re.escape(tableName + "_1m"), tableName + "_10m", SQL, flags=re.IGNORECASE)
                  groupByFields= re.sub(re.escape(tableName + "_1m"), tableName + "_10m", groupByFields, flags=re.IGNORECASE)
                  SQL= re.sub(re.escape(tableName + "_10m"), tableName + "_10m", SQL, flags=re.IGNORECASE)
                  groupByFields= re.sub(re.escape(tableName + "_10m"), tableName + "_10m", groupByFields, flags=re.IGNORECASE)

              elif (scale == "1km"):
                  SQL= re.sub(re.escape(tableName + "_1m"), tableName + "_" + feature.getAttribute('PreviousScale'), SQL, flags=re.IGNORECASE)
                  groupByFields= re.sub(re.escape(tableName + "_1m"), tableName + "_" + feature.getAttribute('PreviousScale'), groupByFields, flags=re.IGNORECASE)
                  SQL= re.sub(re.escape(tableName +"_10m"), tableName + "_" + feature.getAttribute('PreviousScale'), SQL, flags=re.IGNORECASE)
                  groupByFields= re.sub(re.escape(tableName + "_10m"), tableName + "_" + feature.getAttribute('PreviousScale'), groupByFields, flags=re.IGNORECASE)
                  SQL= re.sub(re.escape(tableName + "_100m"), tableName + "_" + feature.getAttribute('PreviousScale'), SQL, flags=re.IGNORECASE)
                  groupByFields= re.sub(re.escape(tableName + "_100m"), tableName + "_" + feature.getAttribute('PreviousScale'), groupByFields, flags=re.IGNORECASE)


              elif (scale == "10km"):
                  SQL= re.sub(re.escape(tableName + "_1m"), tableName +"_" + feature.getAttribute('PreviousScale'), SQL, flags=re.IGNORECASE)
                  groupByFields= re.sub(re.escape(tableName + "_1m"), tableName + "_" + feature.getAttribute('PreviousScale'), groupByFields, flags=re.IGNORECASE)
                  SQL= re.sub(re.escape(tableName + "_10m"), tableName +"_" + feature.getAttribute('PreviousScale'), SQL, flags=re.IGNORECASE)
                  groupByFields= re.sub(re.escape(tableName + "_10m"), tableName + "_" + feature.getAttribute('PreviousScale'), groupByFields, flags=re.IGNORECASE)
                  SQL= re.sub(re.escape(tableName + "_100m"), tableName +"_" + feature.getAttribute('PreviousScale'), SQL, flags=re.IGNORECASE)
                  groupByFields= re.sub(re.escape(tableName + "_100m"), tableName + "_" + feature.getAttribute('PreviousScale'), groupByFields, flags=re.IGNORECASE)
                  SQL= re.sub(re.escape(tableName + "_1km"), tableName  +"_" + feature.getAttribute('PreviousScale'), SQL, flags=re.IGNORECASE)
                  groupByFields= re.sub(re.escape(tableName + "_1km"), tableName + "_" + feature.getAttribute('PreviousScale'), groupByFields, flags=re.IGNORECASE)

              last = int(feature.getAttribute('Last'))
              #if (last ==1):
              #    SQL = SQL + ")"

              feature.setAttribute("F_TableTSQLHighToLow",SQL)
              feature.setAttribute("_SQL_GroupBy_Fields_HighToLow",groupByFields)
              self.pyoutput(feature)
          def close(self):
              pass
    PYTHONSYMBOL = FeatureProcessor
    -> Output (output)
AttributeCreator_2
    ATTR_TABLE:
      SET_TO F_TableNameHighToLow = @Value(F_TableName)_HighToLow
      SET_TO F_TableTSQLHighToLow = SELECT
            G.`GridNum10km`,
            G.`GridNum@Value(GridTypeName)` as GridNum,
            @Value(_SQLFieldsHighToLow),
          (sum(
             case
               when @Value(F_TableName)_HighToLow_@Value(PreviousScale).areaha is not null then @Value(F_TableName)_HighToLow_@Value(PreviousScale).areaha
               else @Value(F_TableName)_@Value(DimGridTypeName).areaha
             end
           )) as areaHa
        FROM
           jedi_cubes.@Value(G_TableName)_HighToLow_@Value(DimGridTypeName) as G
           LEFT JOIN
            jedi_cubes.@Value(F_TableName)_@Value(DimGridTypeName) on
            G.GridNum@Value(DimGridTypeName)=@Value(F_TableName)_@Value(DimGridTypeName).gridnum@Value(DimGridTypeName) and G.gridnum10km=@Value(F_TableName)_@Value(DimGridTypeName).gridnum10km
          LEFT JOIN
                jedi_cubes.@Value(F_TableName)_HighToLow_@Value(PreviousScale)  ON G.gridnum@Value(DimGridTypeName)=  jedi_cubes.@Value(F_TableName)_HighToLow_@Value(PreviousScale).GridNum@Value(DimGridTypeName)
                and G.gridnum10km=jedi_cubes.@Value(F_TableName)_HighToLow_@Value(PreviousScale).GridNum10km
        GROUP BY
            G.`GridNum10km`,
            G.`GridNum@Value(GridTypeName)`
      SET_TO Last = 1
    -> PythonCaller
AttributeCreator_3
    ATTR_TABLE:
      SET_TO F_TableNameHighToLow = @Value(F_TableName)_HighToLow_@Value(DimGridTypeName)
      SET_TO F_TableTSQLHighToLow = FME_CONDITIONAL:DEFAULT_VALUE'SELECT
            G.`GridNum10km`,
            G.`GridNum@Value(NextScale)` as GridNum@Value(NextScale),
            @Value(_SQLFieldsHighToLow),
          (sum(
             case
               when @Value(F_TableName)_HighToLow_@Value(PreviousScale).areaha is not null then @Value(F_TableName)_HighToLow_@Value(PreviousScale).areaha
               else @Value(F_TableName)_@Value(DimGridTypeName).areaha
             end
           )) as areaHa
        FROM
            jedi_cubes.@Value(G_TableName)_HighToLow_@Value(DimGridTypeName) as G LEFT JOIN
            jedi_cubes.@Value(F_TableName)_@Value(DimGridTypeName) on
            G.GridNum@Value(DimGridTypeName)=@Value(F_TableName)_@Value(DimGridTypeName).gridnum@Value(DimGridTypeName) and G.gridnum10km=@Value(F_TableName)_@Value(DimGridTypeName).gridnum10km
          LEFT JOIN
             jedi_cubes.@Value(F_TableName)_@Value(PreviousScale) ON G.gridnum@Value(DimGridTypeName)= jedi_cubes.@Value(F_TableName)_HighToLow_@Value(PreviousScale).GridNum@Value(DimGridTypeName)
                and G.gridnum10km=jedi_cubes.@Value(F_TableName)_@Value(PreviousScale) .GridNum10km
        GROUP BY
           G.`GridNum10km`,
           G.`GridNum@Value(NextScale)`
        'BOOL_OP;OR;COMPOSITE_TEST;1;TEST @Value(NextScale) = 10km'SELECT
            G.`GridNum10km`,
            @Value(_SQLFieldsHighToLow),
          (sum(
             case
               when @Value(F_TableName)_HighToLow_@Value(PreviousScale).areaha is not null then @Value(F_TableName)_HighToLow_@Value(PreviousScale).areaha
               else @Value(F_TableName)_@Value(DimGridTypeName).areaha
             end
           )) as areaHa
        FROM
            jedi_cubes.@Value(G_TableName)_HighToLow_@Value(DimGridTypeName) as G LEFT JOIN
            jedi_cubes.@Value(F_TableName)_@Value(DimGridTypeName) on
            G.GridNum@Value(DimGridTypeName)=@Value(F_TableName)_@Value(DimGridTypeName).gridnum@Value(DimGridTypeName) and G.gridnum10km=@Value(F_TableName)_@Value(DimGridTypeName).gridnum10km
          LEFT JOIN
             jedi_cubes.@Value(F_TableName)_@Value(PreviousScale) ON G.gridnum@Value(DimGridTypeName)= jedi_cubes.@Value(F_TableName)_HighToLow_@Value(PreviousScale).GridNum@Value(DimGridTypeName)
                and G.gridnum10km=jedi_cubes.@Value(F_TableName)_@Value(PreviousScale) .GridNum10km
        GROUP BY
           G.`GridNum10km`,
           G.`GridNum@Value(NextScale)`
        'FME_NUM_CONDITIONS2___
      SET_TO Last = 0
    -> PythonCaller
PythonCaller
    PYTHONSOURCE:
      import fme
      import fmeobjects
      import re


      # Template Function interface:
      # When using this function, make sure its name is set as the value of
      # the 'Class or Function to Process Features' transformer parameter
      def processFeature(feature):
          pass

      # Template Class Interface:
      # When using this class, make sure its name is set as the value of
      # the 'Class or Function to Process Features' transformer parameter
      class FeatureProcessor(object):
          def __init__(self):
              pass
          def input(self,feature):
              scale = feature.getAttribute('DimGridTypeName')
              SQL = feature.getAttribute('F_TableTSQLHighToLow')
              tableName = feature.getAttribute('F_TableName')
              groupByFields = feature.getAttribute('_SQL_GroupBy_Fields_HighToLow')


              if (scale == "10m"):
                  SQL= re.sub(re.escape(tableName + "_1m"), tableName + "_HighToLow_1m", SQL, flags=re.IGNORECASE)
                  groupByFields= re.sub(re.escape(tableName + "_1m"), tableName + "_HighToLow_1m", groupByFields, flags=re.IGNORECASE)

              elif (scale == "100m"):
                  SQL= re.sub(re.escape(tableName + "_1m"), tableName + "_HighToLow_10m", SQL, flags=re.IGNORECASE)
                  groupByFields= re.sub(re.escape(tableName + "_1m"), tableName + "_HighToLow_10m", groupByFields, flags=re.IGNORECASE)
                  SQL= re.sub(re.escape(tableName + "_10m"), tableName + "_HighToLow_10m", SQL, flags=re.IGNORECASE)
                  groupByFields= re.sub(re.escape(tableName + "_10m"), tableName + "_HighToLow_10m", groupByFields, flags=re.IGNORECASE)

              elif (scale == "1km"):
                  SQL= re.sub(re.escape(tableName + "_1m"), tableName + "_HighToLow_" + feature.getAttribute('PreviousScale'), SQL, flags=re.IGNORECASE)
                  groupByFields= re.sub(re.escape(tableName + "_1m"), tableName + "_HighToLow_" + feature.getAttribute('PreviousScale'), groupByFields, flags=re.IGNORECASE)
                  SQL= re.sub(re.escape(tableName +"_10m"), tableName + "_HighToLow_" + feature.getAttribute('PreviousScale'), SQL, flags=re.IGNORECASE)
                  groupByFields= re.sub(re.escape(tableName + "_10m"), tableName + "_HighToLow_" + feature.getAttribute('PreviousScale'), groupByFields, flags=re.IGNORECASE)
                  SQL= re.sub(re.escape(tableName + "_100m"), tableName + "_HighToLow_" + feature.getAttribute('PreviousScale'), SQL, flags=re.IGNORECASE)
                  groupByFields= re.sub(re.escape(tableName + "_100m"), tableName + "_HighToLow_" + feature.getAttribute('PreviousScale'), groupByFields, flags=re.IGNORECASE)


              elif (scale == "10km"):
                  SQL= re.sub(re.escape(tableName + "_1m"), tableName +"_HighToLow_" + feature.getAttribute('PreviousScale'), SQL, flags=re.IGNORECASE)
                  groupByFields= re.sub(re.escape(tableName + "_1m"), tableName + "_HighToLow_" + feature.getAttribute('PreviousScale'), groupByFields, flags=re.IGNORECASE)
                  SQL= re.sub(re.escape(tableName + "_10m"), tableName +"_HighToLow_" + feature.getAttribute('PreviousScale'), SQL, flags=re.IGNORECASE)
                  groupByFields= re.sub(re.escape(tableName + "_10m"), tableName + "_HighToLow_" + feature.getAttribute('PreviousScale'), groupByFields, flags=re.IGNORECASE)
                  SQL= re.sub(re.escape(tableName + "_100m"), tableName +"_HighToLow_" + feature.getAttribute('PreviousScale'), SQL, flags=re.IGNORECASE)
                  groupByFields= re.sub(re.escape(tableName + "_100m"), tableName + "_HighToLow_" + feature.getAttribute('PreviousScale'), groupByFields, flags=re.IGNORECASE)
                  SQL= re.sub(re.escape(tableName + "_1km"), tableName  +"_HighToLow_" + feature.getAttribute('PreviousScale'), SQL, flags=re.IGNORECASE)
                  groupByFields= re.sub(re.escape(tableName + "_1km"), tableName + "_HighToLow_" + feature.getAttribute('PreviousScale'), groupByFields, flags=re.IGNORECASE)

              last = int(feature.getAttribute('Last'))
              #if (last ==1):
              #    SQL = SQL + ")"

              feature.setAttribute("F_TableTSQLHighToLow",SQL)
              feature.setAttribute("_SQL_GroupBy_Fields_HighToLow",groupByFields)
              self.pyoutput(feature)
          def close(self):
              pass
    PYTHONSYMBOL = FeatureProcessor
    -> Output (output)
Output (output)
Note: All scales but the 1st
TestFilter [off]
    DEFAULT_VALUE = LowestScale
    TEST_LIST = BOOL_OP,OR,COMPOSITE_TEST,<Unused>,TEST_CLAUSE,"TEST @Value(_minDimGridSpacing) != @Value(DimGridSpacing)",OtherScale
    OtherScale -> PreviousScale
Note: Set previous scales
PreviousScale: AttributeCreator
    ATTR_TABLE:
      SET_TO PreviousScale = FME_CONDITIONAL:DEFAULT_VALUE'_FME_NO_OP_'BOOL_OP;OR;COMPOSITE_TEST;1;TEST @Value(DimGridSpacing) = 10'1m'BOOL_OP;OR;COMPOSITE_TEST;1;TEST @Value(DimGridSpacing) = 100'10m'BOOL_OP;OR;COMPOSITE_TEST;1;TEST @Value(DimGridSpacing) = 1000'100m'BOOL_OP;OR;COMPOSITE_TEST;1;TEST @Value(DimGridSpacing) = 10000'1km'FME_NUM_CONDITIONS5___
      SET_TO RemoveFromQuery = FME_CONDITIONAL:DEFAULT_VALUE'_FME_NO_OP_'BOOL_OP;OR;COMPOSITE_TEST;1;TEST @Value(DimGridSpacing) = 10'100m,1km,10km'BOOL_OP;OR;COMPOSITE_TEST;1;TEST @Value(DimGridSpacing) = 100'1km,10km'BOOL_OP;OR;COMPOSITE_TEST;1;TEST @Value(DimGridSpacing) = 1000'10km'FME_NUM_CONDITIONS4___
      SET_TO NextScale = FME_CONDITIONAL:DEFAULT_VALUE'10km'BOOL_OP;OR;COMPOSITE_TEST;1;TEST @Value(DimGridSpacing) = 10'100m'BOOL_OP;OR;COMPOSITE_TEST;1;TEST @Value(DimGridSpacing) = 100'1km'FME_NUM_CONDITIONS3___
TestFilter_2
    DEFAULT_VALUE = Ignore
    TEST_LIST = BOOL_OP,OR,COMPOSITE_TEST,<Unused>,TEST_CLAUSE,"TEST @Value(_TotalGridTypes) = 1",OnlyOneGridType
    OnlyOneGridType -> OneGridType (output)
OneGridType (output)

Bookmark: Remove fields of no neccessary scales
AttributeSplitter
    ATTR_NAME = RemoveFromQuery
    DELIMITER = ,
    DROP_EMPTY_PARTS = No
    LIST_NAME = _list
    TRIM_OPTION = Both
    -> ListElementCounter
Note: Count how many to remove
ListElementCounter
    CNT_ATTR = _TotalScalesToRemove
    LIST_NAME = _list{}
    -> ReplaceFieldsFromNoScale
ReplaceFieldsFromNoScale
    F_TABLENAME = @Value(F_TableName)
    LIST_ATTR = _list{}
    _SQLFIELDSHIGHTOLOW = @Value(_SQLFieldsHighToLow)
    _SQL_GROUPBY_FIELDS_HIGHTOLOW = @Value(_SQL_GroupBy_Fields_HighToLow)
    _TOTALSCALESTOREMOVE = @Value(_TotalScalesToRemove)
    -> StringReplacer
StringReplacer
    CASE = NO
    FIND_TEXT = "\t\t"
    NO_MATCH = _FME_NO_OP_
    REGEXP = NO
    SRC_ATTRS = _SQL_GroupBy_Fields_HighToLow,_SQLFieldsHighToLow
    -> GridNumTranslator

FME custom transformer BuildCTableFields

Parameters:
- F_TABLENAME =
- TMODE_NAME =
- _AGGREGATEFUNCTION =
- _FIELDALIAS =

Input (input)
    -> FeatureMerger_2 [REQUESTOR]
    -> AttributeCreator_24
AttributeCreator_24
    ATTR_TABLE = SET_TO CTable_Fields = FME_CONDITIONAL:DEFAULT_VALUE'@Value(F_TableName).@Value(_FieldAlias)  as @Value(_FieldAlias)'BOOL_OP;AND;COMPOSITE_TEST;1 AND 2;TEST NoModeFields NOT_ATTRIBUTE_HAS_A_VALUE _FME_BLANK_STRING_;TEST @Value(_AggregateFunction) = MODE'(select @Value(_FieldAlias)  from jedi_cubes.@Value(TMODE_Name)_C_@Value(_FieldAlias)) as @Value(_FieldAlias)'BOOL_OP;AND;COMPOSITE_TEST;1 AND 2;TEST NoModeFields ATTRIBUTE_HAS_A_VALUE _FME_BLANK_STRING_;TEST @Value(_AggregateFunction) = MODE'jedi_cubes.@Value(TMODE_Name)_C_@Value(_FieldAlias).@Value(_FieldAlias) as @Value(_FieldAlias)'BOOL_OP;AND;COMPOSITE_TEST;1;TEST _AggregateFunction ATTRIBUTE_HAS_A_VALUE _FME_BLANK_STRING_'@Value(_AggregateFunction)(@Value(F_TableName).@Value(_FieldAlias))  as @Value(_FieldAlias)'FME_NUM_CONDITIONS4___
    -> Aggregator_7
Aggregator_7
    ACCUM_ATTRS_NAME = Use Attributes From One Feature
    AGGREGATE_TYPE = Homogeneous Collection (If Possible)
    CONCAT_ATTRS = CTable_Fields
    MODE = Geometry - Assemble One Level
    SEP = ,
    AGGREGATE -> FeatureMerger_2 [SUPPLIER]
FeatureMerger_2
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> Output (output)
Output (output)

FME custom transformer SQLModeFieldNameCompiler

Parameters:
- AddAfterField =
- AggregateFunction =
- DatabaseOwner =
- DimsPerGroup =
- FieldAlias =
- FieldName =
- Include_Agg =
- TableName =
- TargetAttribute =
- TotalIndents =

Input (input)
    -> Counter
Counter
    CNT_ATTR = _count
    DOMAIN = counter
    SCOPE = Local
    START = 0
    -> AttributeCreator_5
Note: Add NumGroup
AttributeCreator_5
    ATTR_TABLE = SET_TO NumGroupTableA = @int(@Value(_count)/$(DimsPerGroup))
    -> FeatureMerger [REQUESTOR]
    -> StringSearcher
Note: TargetAttribute receiving the final result
StringSearcher
    CASE = no
    MATCHED_RESULT_ATTR = $(TargetAttribute)
    REGEXP = a
    STRING_TO_SEARCH = a
    MATCHED -> ParameterFetcher
ParameterFetcher
    ATTR_LIST = _FieldAlias $(FieldAlias) _FieldName $(FieldName) _TableName $(TableName) _TargetAttribute $(TargetAttribute) _DatabaseOwner $(DatabaseOwner) _TotalIndents $(TotalIndents) _AddAfterField $(AddAfterField) _AggregateFunction $(AggregateFunction)
    -> AttributeCreator_3
Note: Compile SQL syntax depending / on the informaton provided / [Database owner]
AttributeCreator_3
    ATTR_TABLE = SET_TO __SQLFieldNames = FME_CONDITIONAL:DEFAULT_VALUE''BOOL_OP;AND;COMPOSITE_TEST;<Unused>;TEST @Value(_DatabaseOwner) ATTRIBUTE_HAS_VALUE _FME_BLANK_STRING_'@Value(_DatabaseOwner).'FME_NUM_CONDITIONS2___
    -> AttributeCreator_4
Note: Compile SQL syntax depending / on the informaton provided / [TableName].[FieldName]
AttributeCreator_4
    ATTR_TABLE = SET_TO __SQLFieldNames = FME_CONDITIONAL:DEFAULT_VALUE'`@Value(_FieldName)`'BOOL_OP;AND;COMPOSITE_TEST;<Unused>;TEST @Value(_TableName) ATTRIBUTE_HAS_VALUE _FME_BLANK_STRING_'@Value(__SQLFieldNames)`@Value(_TableName)`.`@Value(_FieldName)`'FME_NUM_CONDITIONS2___
    -> TestFilter
Note: Do we make a count or sum / on this field?
TestFilter
    DEFAULT_VALUE = Plain
    TEST_LIST = "BOOL_OP,OR,COMPOSITE_TEST,""""""1"""""",TEST_CLAUSE,TEST _AggregateFunction ATTRIBUTE_HAS_A_VALUE """,Agregate
    Agregate -> IS_MODE
    Plain -> AttributeCreator
IS_MODE: TestFilter
    DEFAULT_VALUE = AGG
    TEST_LIST = "BOOL_OP,OR,COMPOSITE_TEST,""""""1"""""",TEST_CLAUSE,TEST @Value(_AggregateFunction) = MODE",MODE
    MODE -> AttributeCreator_7
    AGG -> TestFilter_2
Note: Buid Field, count(Filed)
AttributeCreator_7
    ATTR_TABLE = SET_TO __SQLFieldNames = (`TMODE_@Value(_FieldName)`.`@Value(_FieldName)`)
    -> AttributeCreator_2
TestFilter_2
    DEFAULT_VALUE = No
    TEST_LIST = "BOOL_OP,OR,COMPOSITE_TEST,""""""1"""""",TEST_CLAUSE,TEST $(Include_Agg) = Yes",AGG
    AGG -> AttributeCreator_6
    No -> AttributeCreator
Note: Wrap the aggregate function arround / the field and set Alias is provided
AttributeCreator_6
    ATTR_TABLE = SET_TO __SQLFieldNames = @Value(_AggregateFunction)(@Value(__SQLFieldNames)) as `@Value(_FieldName)`
    -> AttributeCreator_2
Note: Compile SQL syntax depending / on the informaton provided / as [Alias]
AttributeCreator
    ATTR_TABLE = SET_TO __SQLFieldNames = @Value(__SQLFieldNames)
    -> AttributeCreator_2
Note: Add something after field
AttributeCreator_2
    ATTR_TABLE = SET_TO __SQLFieldNames = FME_CONDITIONAL:DEFAULT_VALUE'_FME_NO_OP_'BOOL_OP;OR;COMPOSITE_TEST;<Unused>;TEST @Value(_AddAfterField) ATTRIBUTE_HAS_VALUE _FME_BLANK_STRING_'@Value(__SQLFieldNames) @Value(_AddAfterField)'FME_NUM_CONDITIONS2___
    -> StringPadder
Note: Add indents to make the / TSQL look nice
StringPadder
    BLANK_ATTRIBUTE = Yes
    PADCHAR = "\t"
    SIDE = Left
    SRC_ATTRS = __SQLFieldNames
    WIDTH = @Value(_TotalIndents)+@StringLength(@Value(__SQLFieldNames))
    -> Aggregator_2
Note: Make field snippeds unqiue
Aggregator_2
    ACCUM_ATTRS_NAME = Use Attributes From One Feature
    AGGREGATE_TYPE = Homogeneous Collection (If Possible)
    GROUP_BY = __SQLFieldNames
    MODE = Geometry - Assemble One Level
    ORDERED = No
    SEP = ,
    AGGREGATE -> Sorter
Note: Make sure we order / as they came in
Sorter
    SORT_PARM = _count NUMERIC ASCENDING
    SORTED -> Aggregator
Note: Combine them all together
Aggregator
    ACCUM_ATTRS_NAME = Use Attributes From One Feature
    AGGREGATE_TYPE = Homogeneous Collection (If Possible)
    CONCAT_ATTRS = __SQLFieldNames
    GROUP_BY = NumGroupTableA
    MODE = Geometry - Assemble One Level
    ORDERED = No
    SEP = ",\n"
    AGGREGATE -> PythonCaller
Note: Set to users attribute
PythonCaller
    PYTHONSOURCE:
      import fme
      import fmeobjects
      # Template Function interface:
      # When using this function, make sure its name is set as the value of
      # the 'Class or Function to Process Features' transformer parameter
      def processFeature(feature):
          pass

      # Template Class Interface:
      # When using this class, make sure its name is set as the value of
      # the 'Class or Function to Process Features' transformer parameter
      class FeatureProcessor(object):
          def __init__(self):
              pass
          def input(self,feature):
              #
              # Move the new value into the target attribute user has chosen.
              #
              TargetAttribute = feature.getAttribute("_TargetAttribute")
              SQLFieldNames = feature.getAttribute("__SQLFieldNames")
              feature.setAttribute(TargetAttribute,SQLFieldNames)
              self.pyoutput(feature)
          def close(self):
              pass
    PYTHONSYMBOL = FeatureProcessor
    -> AttributeRemover
AttributeRemover
    REMOVE_ATTRS = _AddAfterField,_TableName,_DatabaseOwner,_FieldAlias,__SQLFieldNames,_AggregateFunction,_FieldName,_TargetAttribute
    -> FeatureMerger [SUPPLIER]
Note: Remap new value to all values
FeatureMerger
    ATTR_ACCUM_MODE = Merge Supplier
    ATTR_CONFLICT_RES = Use Requestor
    GROUP_BY = NumGroupTableA
    IGNORE_NULLS = No
    JOIN_KEYS = 1 1 AUTO
    MERGE_TYPE = Attributes Only
    PROCESS_DUPS = NO
    REJECT_NULL_MISSING_KEYS = No
    SUPPLIERS_FIRST = No
    MERGED -> Output (output)
Output (output)

FME custom transformer BuildJoinQueryCondition

Parameters:
- NOMODEFIELDS =
- TMODE_NAME =
- _FIELDNAME =

Input (input)
    -> Counter
Counter
    CNT_ATTR = _count
    DOMAIN = counter
    SCOPE = Local
    START = 0
    -> AttributeSplitter
    -> FeatureMerger [REQUESTOR]
AttributeSplitter
    ATTR_NAME = NoModeFields
    DELIMITER = ,
    DROP_EMPTY_PARTS = Yes
    LIST_NAME = Fields
    TRIM_OPTION = Both
    -> ListElementCounter
ListElementCounter
    CNT_ATTR = _element_count
    LIST_NAME = Fields{}
    -> TesterFieldsExist
TesterFieldsExist
    BOOL_OP = OR
    COMPOSITE_TEST = 1
    TEST_CLAUSE = TEST @Value(_element_count) > 0
    TEST_MODE = TEST
    PASSED -> ListExploder_2
    FAILED -> AttributeCreator
Note: Build a list with the condition fields
ListExploder_2
    ATTR_ACCUM_MODE = Merge List Attributes
    ATTR_CONFLICT_RES = Use List Attribute Values
    INDEX_ATTR = _element_index
    LIST_ATTR = Fields{}
    ELEMENTS -> AttributeSplitter_2
Note: Split table name and field
AttributeSplitter_2
    ATTR_NAME = Fields
    DELIMITER = .
    DROP_EMPTY_PARTS = No
    LIST_NAME = SplitField
    TRIM_OPTION = Both
    -> EqualEachField
EqualEachField: AttributeCreator
    ATTR_TABLE:
      SET_TO join_cond = CASE WHEN isnull(@Value(Fields)) then '#*#' else CAST(@Value(Fields) as string) END  =
            CASE WHEN isnull(jedi_cubes.`@Value(TMODE_Name)_@Value(_FieldName)`.@Value(SplitField{2})) then '#*#' else cast(jedi_cubes.`@Value(TMODE_Name)_@Value(_FieldName)`.@Value(SplitField{2}) as string) END
    -> JoinWithAND
JoinWithAND: Aggregator
    ACCUM_ATTRS_NAME = Use Attributes From One Feature
    AGGREGATE_TYPE = Homogeneous Collection (If Possible)
    CONCAT_ATTRS = join_cond
    GROUP_BY = _count
    MODE = Geometry - Assemble One Level
    SEP = " AND \n "
    AGGREGATE -> AttributeRemover
Note: Empty joincondition as there are no non-agg fields
AttributeCreator
    ATTR_TABLE = SET_TO join_cond
    -> AttributeRemover
AttributeRemover
    LIST_ATTRS = SplitField{}
    REMOVE_ATTRS = SplitField{0},_element_index,Fields
    -> FeatureMerger [SUPPLIER]
FeatureMerger
    ATTR_ACCUM_MODE = Merge Supplier
    ATTR_CONFLICT_RES = Use Requestor
    IGNORE_NULLS = No
    JOIN_KEYS = @Value(_FieldName) @Value(_FieldName) AUTO
    MERGE_TYPE = Attributes Only
    PROCESS_DUPS = NO
    REJECT_NULL_MISSING_KEYS = No
    SUPPLIERS_FIRST = No
    MERGED -> Output (output)
Output (output)

FME custom transformer CreateCubeFields

Parameters:
- CUBEID =

Initiator (input)
    -> SQLExecutor_GetFields [INITIATOR]
SQLExecutor_GetFields
    COMBINE_ATTRS = Result Attributes Only
    COMBINE_GEOM = Initiator Geometry Only
    DATASET = CubeManager
    EXPOSED_ATTRIBUTE_LIST = ColumnName
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = CubeManager
    MSSQL_ADO_QUERY_FEATURE_TYPES_FOR_MERGE_FILTERS = Yes
    SQL_STATEMENT:
      select
      	CubeFieldAlias as ColumnName

      from CubeFields inner join
      	fields on CubeFields.FieldId = Fields.FieldId inner join
      	files on Fields.FileId = files.FileId inner join
      	CubeDimensions on files.CubeDimensionId = CubeDimensions.CubeDimensionId inner join
      	GridTypes on CubeDimensions.GridTypeId = GridTypes.GridTypeId

      where
      	CubeFields.CubeId = @Value(CubeId) and LookupFieldId IS NULL
      	and fields.IgnoreField = 0
      order by
          GridTypes.XCellSpacing,
      	--CubeFields.DimOrder,
      	fields.FieldOrder,
      	CubeFieldAlias
    RESULT -> Aggregator_5
    INITIATOR -> FeatureMerger_2 [SUPPLIER]
Aggregator_5
    ACCUM_ATTRS_NAME = Use Attributes From One Feature
    AGGREGATE_TYPE = Homogeneous Collection (If Possible)
    CONCAT_ATTRS = ColumnName
    MODE = Geometry - Assemble One Level
    SEP = ,
    AGGREGATE -> FeatureMerger_2 [REQUESTOR]
FeatureMerger_2
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> Output (output)
Output (output)

FME custom transformer SQLFieldNameCompiler
Compiles a TSQL snipped for a list of field names.
Parameters:
    Group by: You can group a set of records that should each compile its set of FIELD snippeds. (optional)
    Database owner: The database owner to use, default is 'dbo' (optional)
    Table name: The table the field belongs to. (optional)
    Field name: The field name we want to be part of the snipped.
    Alias name: The field alias name we want to be part of the snipped (OPTIONAL).
    Target attribute: The attribute that will receive the full FIELD snipped.
    Explenation:
If you have complex SQL statements that are generated by FME then this transforer is excelent. The input is a number of features that together should generate one or more FIELD list snippeds. The result will be an additional attribute added to the input features. This allows you to perform a number of snippeds and at the end perform an aggregate or sample the first record. 
An example of such snipped would look like this.
 [dbo].[D_A_CLC_90_56_20161115_100m].[Category] as [CLC90],
 [dbo].[D_A_CLC_00_57_20161115_100m].[Category] as [CLC00],
 [dbo].[D_A_CLC_06_58_20161115_100m].[Category] as [CLC06],
 [dbo].[D_A_CLC_12_59_20161115_100m].[Category] as [CLC12]

Parameters:
- AddAfterField =
- AggregateFunction =
- DatabaseOwner =
- DimGridTypeName =
- DimsPerGroup =
- FieldAlias =
- FieldName =
- TableName =
- TargetAttribute =
- TotalIndents =

Input (input)
    -> Counter
Counter
    CNT_ATTR = _count
    DOMAIN = counter
    SCOPE = Local
    START = 0
    -> StringSearcher
Note: TargetAttribute receiving the final result
StringSearcher
    CASE = no
    MATCHED_RESULT_ATTR = $(TargetAttribute)
    REGEXP = a
    STRING_TO_SEARCH = a
    MATCHED -> ParameterFetcher
ParameterFetcher
    ATTR_LIST = _FieldAlias $(FieldAlias) _FieldName $(FieldName) _TableName $(TableName) _TargetAttribute $(TargetAttribute) _DatabaseOwner $(DatabaseOwner) _TotalIndents $(TotalIndents) _AddAfterField $(AddAfterField) _AggregateFunction $(AggregateFunction) DimGridTypeName $(DimGridTypeName)
    -> FeatureJoiner_3 [LEFT]
    -> AttributeCreator_3
    -> Aggregator_3
Note: Compile SQL syntax depending / on the informaton provided / [Database owner]
AttributeCreator_3
    ATTR_TABLE = SET_TO __SQLFieldNames = FME_CONDITIONAL:DEFAULT_VALUE''BOOL_OP;AND;COMPOSITE_TEST;1;TEST @Value(_DatabaseOwner) ATTRIBUTE_HAS_VALUE _FME_BLANK_STRING_'@Value(_DatabaseOwner).'FME_NUM_CONDITIONS2___
    -> AttributeCreator_4
Note: Compile SQL syntax depending / on the informaton provided / [TableName].[FieldName]
AttributeCreator_4
    ATTR_TABLE = SET_TO __SQLFieldNames = FME_CONDITIONAL:DEFAULT_VALUE'`@LowerCase(@Value(_FieldName))`'BOOL_OP;AND;COMPOSITE_TEST;<Unused>;TEST @Value(_TableName) ATTRIBUTE_HAS_VALUE _FME_BLANK_STRING_'@LowerCase(@Value(__SQLFieldNames))`@Value(_TableName)`.`@LowerCase(@Value(_FieldName))`'FME_NUM_CONDITIONS2___
    -> TestFilter
Note: Do we make a count or sum / on this field?
TestFilter
    DEFAULT_VALUE = Plain
    TEST_LIST = BOOL_OP,OR,COMPOSITE_TEST,<Unused>,TEST_CLAUSE,"TEST @Value(_AggregateFunction) ATTRIBUTE_HAS_VALUE """"",Agregate
    Agregate -> IS_MODE
    Plain -> AttributeCreator
IS_MODE: TestFilter
    DEFAULT_VALUE = AGG
    TEST_LIST = "BOOL_OP,OR,COMPOSITE_TEST,""""""1"""""",TEST_CLAUSE,TEST @Value(_AggregateFunction) = MODE",MODE
    MODE -> AttributeCreator_7
    AGG -> AttributeCreator_5
Note: Buid Field, count(Filed)
AttributeCreator_7
    ATTR_TABLE = SET_TO __SQLFieldNames = FME_CONDITIONAL:DEFAULT_VALUE'@LowerCase(@Value(__SQLFieldNames)) as `@LowerCase(@Trim(@Value(_FieldName)))`'BOOL_OP;AND;COMPOSITE_TEST;1;TEST _FieldAlias ATTRIBUTE_HAS_A_VALUE _FME_BLANK_STRING_'@LowerCase(@Value(__SQLFieldNames)) as `@LowerCase(@Trim(@Value(_FieldAlias)))`'FME_NUM_CONDITIONS2___
    -> AttributeCreator_2
Note: Wrap the aggregate function arround / the field and set Alias is provided
AttributeCreator_5
    ATTR_TABLE = SET_TO __SQLFieldNames = FME_CONDITIONAL:DEFAULT_VALUE'@Value(_AggregateFunction)(@LowerCase(@Value(__SQLFieldNames))) as `@LowerCase(@Trim(@Value(_FieldName)))`'BOOL_OP;AND;COMPOSITE_TEST;<Unused>;TEST @Value(_FieldAlias) ATTRIBUTE_HAS_VALUE _FME_BLANK_STRING_'@Value(_AggregateFunction)(@LowerCase(@Value(__SQLFieldNames)))   as `@LowerCase(@Trim(@Value(_FieldAlias)))`'FME_NUM_CONDITIONS2___
    -> AttributeCreator_2
Note: Compile SQL syntax depending / on the informaton provided / as [Alias]
AttributeCreator
    ATTR_TABLE = SET_TO __SQLFieldNames = FME_CONDITIONAL:DEFAULT_VALUE'@Value(__SQLFieldNames)'BOOL_OP;AND;COMPOSITE_TEST;1;TEST @Value(_FieldAlias) ATTRIBUTE_HAS_VALUE _FME_BLANK_STRING_'@LowerCase(@Value(__SQLFieldNames)) as `@LowerCase(@Trim(@Value(_FieldAlias)))`'FME_NUM_CONDITIONS2___
    -> AttributeCreator_2
Note: Add something after field
AttributeCreator_2
    ATTR_TABLE = SET_TO __SQLFieldNames = FME_CONDITIONAL:DEFAULT_VALUE'_FME_NO_OP_'BOOL_OP;OR;COMPOSITE_TEST;<Unused>;TEST @Value(_AddAfterField) ATTRIBUTE_HAS_VALUE _FME_BLANK_STRING_'@Value(__SQLFieldNames) @Value(_AddAfterField)'FME_NUM_CONDITIONS2___
    -> StringPadder
Note: Add indents to make the / TSQL look nice
StringPadder
    BLANK_ATTRIBUTE = Yes
    PADCHAR = "\t"
    SIDE = Left
    SRC_ATTRS = __SQLFieldNames
    WIDTH = @Value(_TotalIndents)+@StringLength(@Value(__SQLFieldNames))
    -> Aggregator_2
Note: Make field snippeds unqiue
Aggregator_2
    ACCUM_ATTRS_NAME = Use Attributes From One Feature
    AGGREGATE_TYPE = Homogeneous Collection (If Possible)
    GROUP_BY = __SQLFieldNames
    MODE = Geometry - Assemble One Level
    ORDERED = No
    SEP = ,
    AGGREGATE -> FeatureJoiner [LEFT]
Note: We only extract the unique tables
Aggregator_3
    ACCUM_ATTRS_NAME = Use Attributes From One Feature
    AGGREGATE_TYPE = Homogeneous Collection (If Possible)
    GROUP_BY = _TableName DimGridTypeName
    MODE = Geometry - Assemble One Level
    ORDERED = No
    SEP = ,
    AGGREGATE -> Sorter_2
Sorter_2
    SORT_PARM = DimGridTypeName ALPHA DESCENDING _TableName ALPHA ASCENDING
    SORTED -> TestFilter_2
TestFilter_2
    DEFAULT_VALUE = <UNFILTERED>
    TEST_LIST = "BOOL_OP,OR,COMPOSITE_TEST,""""""1"""""",TEST_CLAUSE,TEST @Value(DimGridTypeName) = 10m",10m,"BOOL_OP,OR,COMPOSITE_TEST,""""""1"""""",TEST_CLAUSE,TEST @Value(DimGridTypeName) = 100m",100m,"BOOL_OP,OR,COMPOSITE_TEST,""""""1"""""",TEST_CLAUSE,TEST @Value(DimGridTypeName) = 1km",1km,"BOOL_OP,OR,COMPOSITE_TEST,""""""1"""""",TEST_CLAUSE,TEST @Value(DimGridTypeName) = 10km",10km
    10m -> Counter_2
    100m -> Counter_3
    1km -> Counter_4
    10km -> Counter_5
Counter_2
    CNT_ATTR = _count_tables
    DOMAIN = counter10m
    SCOPE = Local
    START = 1
    -> AttributeCreator_6
Counter_3
    CNT_ATTR = _count_tables
    DOMAIN = counter100m
    SCOPE = Local
    START = 1
    -> AttributeCreator_6
Counter_4
    CNT_ATTR = _count_tables
    DOMAIN = counter1km
    SCOPE = Local
    START = 1
    -> AttributeCreator_6
Counter_5
    CNT_ATTR = _count_tables
    DOMAIN = counter10km
    SCOPE = Local
    START = 1
    -> AttributeCreator_6
AttributeCreator_6
    ATTR_TABLE = SET_TO NumGroup = @Evaluate(@int(@Value(_count_tables)/$(DimsPerGroup)))
    -> AttributeKeeper
AttributeKeeper
    CREATE_BULK_MODE_FEATURES = NO
    KEEP_ATTRS = _TableName,NumGroup
    -> FeatureJoiner [RIGHT]
FeatureJoiner
    ATTR_CONFLICT_RES = Use Right
    GEOMETRY_HANDLING = Use Left
    JOIN_KEYS = _TableName _TableName AUTO
    JOIN_MODE = Inner
    JOINED -> Sorter
Note: Make sure we order / as they came in
Sorter
    SORT_PARM = NumGroup NUMERIC ASCENDING _count NUMERIC ASCENDING
    SORTED -> Aggregator
    SORTED -> FeatureJoiner_2 [LEFT]
Note: Combine them all together
Aggregator
    ACCUM_ATTRS_NAME = Use Attributes From One Feature
    AGGREGATE_TYPE = Homogeneous Collection (If Possible)
    CONCAT_ATTRS = __SQLFieldNames
    GROUP_BY = NumGroup DimGridTypeName
    MODE = Geometry - Assemble One Level
    ORDERED = No
    SEP = ",\n"
    AGGREGATE -> PythonCaller [off]
    AGGREGATE -> AttributeKeeper_2
AttributeKeeper_2
    CREATE_BULK_MODE_FEATURES = NO
    KEEP_ATTRS = __SQLFieldNames,DimGridTypeName,NumGroup
    -> FeatureJoiner_2 [RIGHT]
FeatureJoiner_2
    ATTR_CONFLICT_RES = Use Right
    GEOMETRY_HANDLING = Use Left
    JOIN_KEYS = DimGridTypeName DimGridTypeName AUTO NumGroup NumGroup AUTO
    JOIN_MODE = Inner
    JOINED -> PythonCaller
Note: Set to users attribute
PythonCaller
    PYTHONSOURCE:
      import fme
      import fmeobjects
      # Template Function interface:
      # When using this function, make sure its name is set as the value of
      # the 'Class or Function to Process Features' transformer parameter
      def processFeature(feature):
          pass

      # Template Class Interface:
      # When using this class, make sure its name is set as the value of
      # the 'Class or Function to Process Features' transformer parameter
      class FeatureProcessor(object):
          def __init__(self):
              pass
          def input(self,feature):
              #
              # Move the new value into the target attribute user has chosen.
              #
              TargetAttribute = feature.getAttribute("_TargetAttribute")
              SQLFieldNames = feature.getAttribute("__SQLFieldNames")
              feature.setAttribute(TargetAttribute,SQLFieldNames)
              self.pyoutput(feature)
          def close(self):
              pass
    PYTHONSYMBOL = FeatureProcessor
    -> AttributeCreator_8
AttributeCreator_8
    ATTR_TABLE = SET_TO SQLFields = @Value(__SQLFieldNames)
    -> AttributeRemover
AttributeRemover
    REMOVE_ATTRS = _AddAfterField,_TableName,_DatabaseOwner,__SQLFieldNames,_AggregateFunction,_FieldName,_TargetAttribute,_count
    -> FeatureJoiner_3 [RIGHT]
FeatureJoiner_3
    ATTR_CONFLICT_RES = Use Right
    GEOMETRY_HANDLING = Use Left
    JOIN_KEYS = DimGridTypeName DimGridTypeName AUTO _FieldAlias _FieldAlias AUTO
    JOIN_MODE = Inner
    JOINED -> AttributeRemover_2
AttributeRemover_2
    REMOVE_ATTRS = _count
    -> Output (output)
Output (output)

FME custom transformer BuildModeQuery

Parameters:
- AddAfterField =
- AddGridNums =
- AggregateFunction =
- DatabaseOwner =
- FieldName =
- NOMODEFIELDS =
- NUMGROUPTABLEA =
- TMODE_NAME =
- TableName =
- TargetAttribute =
- TotalIndents =

Input (input)
    -> AttributeCreator_3
AttributeCreator_3
    ATTR_TABLE = SET_TO NoModeFieldsAux = @Value(NoModeFields)
    -> StringReplacer
StringReplacer
    CASE = NO
    FIND_TEXT = `TMODE_[a-z,\,A-Z,_, ,\.,0-9,\-,\(,\),\)]{1,}`\.
    NO_MATCH = _FME_NO_OP_
    REGEXP = YES
    SRC_ATTRS = NoModeFieldsAux
    -> Counter
Counter
    CNT_ATTR = _count
    DOMAIN = counter
    SCOPE = Local
    START = 0
    -> StringSearcher
    -> FeatureJoiner [LEFT]
Note: TargetAttribute receiving the final result
StringSearcher
    CASE = no
    MATCHED_RESULT_ATTR = $(TargetAttribute)
    REGEXP = a
    STRING_TO_SEARCH = a
    MATCHED -> ParameterFetcher
ParameterFetcher
    ATTR_LIST = _FieldName $(FieldName) _TableName $(TableName) _TargetAttribute $(TargetAttribute) _DatabaseOwner $(DatabaseOwner) _TotalIndents $(TotalIndents) _AddAfterField $(AddAfterField) _AggregateFunction $(AggregateFunction)
    -> AttributeCreator
AttributeCreator
    ATTR_TABLE:
      SET_TO GridNumCond = FME_CONDITIONAL:DEFAULT_VALUE' 'BOOL_OP;OR;COMPOSITE_TEST;1;TEST $(AddGridNums) = Yes'    jedi_cubes.@Value(_TableName).GridNum10km = `@Value(TMODE_Name)_@Value(_FieldName)`.GRIDNUM10Km AND
            jedi_cubes.@Value(_TableName).GridNum = `@Value(TMODE_Name)_@Value(_FieldName)`.GRIDNUM  'FME_NUM_CONDITIONS2___
      SET_TO TAGridNumCond = FME_CONDITIONAL:DEFAULT_VALUE' 'BOOL_OP;OR;COMPOSITE_TEST;1;TEST $(AddGridNums) = Yes'        TA.`GridNum10km`,
                TA.`GridNum`,'FME_NUM_CONDITIONS2___
      SET_TO T1GridNumCond = FME_CONDITIONAL:DEFAULT_VALUE' 'BOOL_OP;OR;COMPOSITE_TEST;1;TEST $(AddGridNums) = Yes'		T1.`GridNum10km`,
                T1.`GridNum`,
        'FME_NUM_CONDITIONS2___
    -> CreateInnerQueryFields
CreateInnerQueryFields: AttributeCreator
    ATTR_TABLE:
      SET_TO TAFields = @ReplaceString(@ReplaceString(@Value(NoModeFieldsAux),`@Value(_TableName)`,TA),"jedi_cubes.","")
      SET_TO T1Fields = @ReplaceString(@ReplaceString(@Value(NoModeFieldsAux),`@Value(_TableName)`,T1),"jedi_cubes.","")
    -> TestFilter
Note: Do we make a count or sum / on this field?
TestFilter
    DEFAULT_VALUE = Plain
    TEST_LIST = "BOOL_OP,OR,COMPOSITE_TEST,""""""1"""""",TEST_CLAUSE,TEST _AggregateFunction ATTRIBUTE_HAS_A_VALUE """,Agregate
    Agregate -> IS_MODE
    Plain -> AttributeCreator_2
IS_MODE: TestFilter
    DEFAULT_VALUE = AGG
    TEST_LIST = "BOOL_OP,OR,COMPOSITE_TEST,""""""1"""""",TEST_CLAUSE,TEST @Value(_AggregateFunction) = MODE",MODE
    MODE -> BuildJoinQueryCondition
    AGG -> AttributeCreator_2
BuildJoinQueryCondition
    NOMODEFIELDS = @Value(NoModeFieldsAux)
    TMODE_NAME = @Value(TMODE_Name)
    _FIELDNAME = @Value(_FieldName)
    -> AttributeCreator_7
Note: Build MODE subquery and JOIN criteria
AttributeCreator_7
    ATTR_TABLE:
      SET_TO __SQLFieldNames = FME_CONDITIONAL:DEFAULT_VALUE'LEFT JOIN jedi_cubes.`@Value(TMODE_Name)_@Value(_FieldName)`   ON
             @Value(GridNumCond)
        'BOOL_OP;OR;COMPOSITE_TEST;1;TEST NoModeFields ATTRIBUTE_HAS_A_VALUE _FME_BLANK_STRING_'LEFT JOIN jedi_cubes.`@Value(TMODE_Name)_@Value(_FieldName)`   ON
             @Value(GridNumCond) AND
            @Value(join_cond)'FME_NUM_CONDITIONS2___
      SET_TO CachedModeSubQuery = FME_CONDITIONAL:DEFAULT_VALUE'drop table if exists jedi_cubes.`@Value(TMODE_Name)_@Value(_FieldName)`;
        SELECT
                GridNum10Km,
                GridNum,
                @Value(_FieldName)
                FROM
        (SELECT
                GridNum10Km,
                GridNum,
                @Value(_FieldName),
                row_number()
         OVER (PARTITION BY GridNum10Km, GridNum ORDER BY sum(areaHa) DESC ) as MODE
         FROM jedi_cubes.`@Value(_TableName)`
         GROUP BY
                 GridNum10Km,
                GridNum,
                @Value(_FieldName)
        ) WHERE MODE = 1 'BOOL_OP;OR;COMPOSITE_TEST;1;TEST NoModeFields ATTRIBUTE_HAS_A_VALUE _FME_BLANK_STRING_'drop table if exists jedi_cubes.`@Value(TMODE_Name)_@Value(_FieldName)`;
        SELECT
                GridNum10Km,
                GridNum,
                @ReplaceString(@ReplaceString(@ReplaceString(@Value(NoModeFields),`@Value(_TableName)`.,""),"jedi_cubes.",""),@Value(_TableName).,"") ,
                @Value(_FieldName)
                FROM
        (SELECT
                GridNum10Km,
                GridNum,
                @ReplaceString(@ReplaceString(@Value(NoModeFields),`@Value(_TableName)`.,""),"jedi_cubes.",""),
                @Value(_FieldName),
                row_number()
         OVER (PARTITION BY GridNum10Km, GridNum,@Value(NoModeFields) ORDER BY sum(areaHa) DESC ) as MODE
         FROM jedi_cubes.`@Value(_TableName)`
         GROUP BY
                 GridNum10Km,
                GridNum,
                @Value(NoModeFields),
                @Value(_FieldName)
        )  WHERE MODE = 1 'FME_NUM_CONDITIONS2___
      SET_TO join_cond = FME_CONDITIONAL:DEFAULT_VALUE'_FME_NO_OP_'BOOL_OP;OR;COMPOSITE_TEST;1;TEST NoModeFields ATTRIBUTE_HAS_A_VALUE _FME_BLANK_STRING_'AND @Value(join_cond) 'FME_NUM_CONDITIONS2___
    -> AttributeCreator_2
Note: Add something after field
AttributeCreator_2
    ATTR_TABLE = SET_TO __SQLFieldNames = FME_CONDITIONAL:DEFAULT_VALUE'_FME_NO_OP_'BOOL_OP;OR;COMPOSITE_TEST;<Unused>;TEST @Value(_AddAfterField) ATTRIBUTE_HAS_VALUE _FME_BLANK_STRING_'@Value(__SQLFieldNames) @Value(_AddAfterField)'FME_NUM_CONDITIONS2___
    -> StringPadder
Note: Add indents to make the / TSQL look nice
StringPadder
    BLANK_ATTRIBUTE = Yes
    PADCHAR = "\t"
    SIDE = Left
    SRC_ATTRS = __SQLFieldNames
    WIDTH = @Value(_TotalIndents)+@StringLength(@Value(__SQLFieldNames))
    -> Aggregator_2
Note: Make field snippeds unqiue
Aggregator_2
    ACCUM_ATTRS_NAME = Use Attributes From One Feature
    AGGREGATE_TYPE = Homogeneous Collection (If Possible)
    GROUP_BY = __SQLFieldNames
    MODE = Geometry - Assemble One Level
    ORDERED = No
    SEP = ,
    AGGREGATE -> Sorter
Note: Make sure we order / as they came in
Sorter
    SORT_PARM = _count NUMERIC ASCENDING
    SORTED -> ModeField
    SORTED -> AttributeKeeper_2
Note: Create ModeFields attribuite
ModeField: AttributeCreator
    ATTR_TABLE = SET_TO ModeFields = FME_CONDITIONAL:DEFAULT_VALUE''BOOL_OP;OR;COMPOSITE_TEST;1;TEST @Value(_AggregateFunction) = MODE'jedi_cubes.`@Value(TMODE_Name)_@Value(_FieldName)`.@Value(_FieldName) as @Value(_FieldName),'FME_NUM_CONDITIONS2___
    -> Aggregator
Note: Combine them all together
Aggregator
    ACCUM_ATTRS_NAME = Use Attributes From One Feature
    AGGREGATE_TYPE = Homogeneous Collection (If Possible)
    CONCAT_ATTRS = __SQLFieldNames CachedModeSubQuery ModeFields
    GROUP_BY = NumGroupTableA
    MODE = Geometry - Assemble One Level
    ORDERED = No
    SEP = "\n "
    AGGREGATE -> FeatureJoiner_3 [LEFT]
    AGGREGATE -> TestFilter_3
TestFilter_3
    DEFAULT_VALUE = NoCacheModeValue
    TEST_LIST = "BOOL_OP,OR,COMPOSITE_TEST,""""""1"""""",TEST_CLAUSE,TEST CachedModeSubQuery ATTRIBUTE_HAS_A_VALUE """,CachedModeSubQuery ATTRIBUTE_HAS_A_VALUE
    NoCacheModeValue -> PythonCaller
AttributeKeeper_2
    CREATE_BULK_MODE_FEATURES = NO
    KEEP_ATTRS = CachedModeSubQuery,NumGroupTableA
    -> TestFilter_2
TestFilter_2
    DEFAULT_VALUE = <UNFILTERED>
    TEST_LIST = "BOOL_OP,OR,COMPOSITE_TEST,""""""1"""""",TEST_CLAUSE,TEST CachedModeSubQuery ATTRIBUTE_HAS_A_VALUE """,CachedModeSubQuery
    CachedModeSubQuery -> Aggregator_4
Note: Combine them all together
Aggregator_4
    ACCUM_ATTRS_NAME = Use Attributes From One Feature
    AGGREGATE_TYPE = Homogeneous Collection (If Possible)
    CONCAT_ATTRS = CachedModeSubQuery
    GROUP_BY = NumGroupTableA
    MODE = Geometry - Assemble One Level
    ORDERED = No
    SEP = ","
    AGGREGATE -> FeatureJoiner_3 [RIGHT]
FeatureJoiner_3
    ATTR_CONFLICT_RES = Use Right
    GEOMETRY_HANDLING = Use Left
    JOIN_KEYS = NumGroupTableA NumGroupTableA AUTO
    JOIN_MODE = Inner
    JOINED -> PythonCaller
Note: Set to users attribute
PythonCaller
    PYTHONSOURCE:
      import fme
      import fmeobjects
      # Template Function interface:
      # When using this function, make sure its name is set as the value of
      # the 'Class or Function to Process Features' transformer parameter
      def processFeature(feature):
          pass

      # Template Class Interface:
      # When using this class, make sure its name is set as the value of
      # the 'Class or Function to Process Features' transformer parameter
      class FeatureProcessor(object):
          def __init__(self):
              pass
          def input(self,feature):
              #
              # Move the new value into the target attribute user has chosen.
              #
              TargetAttribute = feature.getAttribute("_TargetAttribute")
              SQLFieldNames = feature.getAttribute("__SQLFieldNames")
              if (SQLFieldNames.startswith(',')):
                  SQLFieldNames= SQLFieldNames[1:]

              if (SQLFieldNames.endswith(',')):
                  SQLFieldNames= SQLFieldNames[:-1]
              feature.setAttribute(TargetAttribute,SQLFieldNames)


              ModeFields = feature.getAttribute("ModeFields")
              if (ModeFields !=""):
                  ModeFields = "\n".join([ll.rstrip() for ll in ModeFields.splitlines() if ll.strip()])
                  ModeFields = ModeFields.strip()

                  if (ModeFields.endswith(',')):
                      ModeFields= ModeFields[:-1]
              feature.setAttribute("ModeFields",ModeFields)

              self.pyoutput(feature)

          def close(self):
              pass
    PYTHONSYMBOL = FeatureProcessor
    -> AttributeRemover
AttributeRemover
    REMOVE_ATTRS = _AddAfterField,_TableName,_count,_AggregateFunction,_FieldName,_TargetAttribute,T1Fields,_TotalIndents,TAFields,_DatabaseOwner,NoModeFieldsAux
    -> FeatureJoiner_2 [LEFT]
    -> AttributeKeeper
AttributeKeeper
    CREATE_BULK_MODE_FEATURES = NO
    KEEP_ATTRS = CachedModeSubQuery,T1GridNumCond,AllTableAFields
    -> Aggregator_3
Aggregator_3
    ACCUM_ATTRS_NAME = Use Attributes From One Feature
    AGGREGATE_TYPE = Homogeneous Collection (If Possible)
    CONCAT_ATTRS = CachedModeSubQuery
    MODE = Geometry - Assemble One Level
    SEP = ","
    AGGREGATE -> FeatureJoiner_2 [RIGHT]
FeatureJoiner_2
    ATTR_CONFLICT_RES = Use Right
    GEOMETRY_HANDLING = Use Left
    JOIN_KEYS = T1GridNumCond T1GridNumCond AUTO
    JOIN_MODE = Inner
    JOINED -> FeatureJoiner [RIGHT]
FeatureJoiner
    ATTR_CONFLICT_RES = Use Left
    GEOMETRY_HANDLING = Use Left
    JOIN_KEYS = NumGroupTableA NumGroupTableA AUTO
    JOIN_MODE = Inner
    JOINED -> Output (output)
Output (output)

FME custom transformer F_GridNumCalculator

Parameters:
- DIMGRIDTYPENAME =
- G_TABLENAME =

Input (input)
    -> Aggregator
    -> FeatureMerger [REQUESTOR]
Note: Aggegrate by GridType / (100m,1km,10km)
Aggregator
    ACCUM_ATTRS_NAME = Use Attributes From One Feature
    AGGREGATE_TYPE = Homogeneous Collection (If Possible)
    GROUP_BY = DimGridTypeName
    MODE = Geometry - Assemble One Level
    ORDERED = No
    SEP = ,
    AGGREGATE -> AttributeCreator_4
Note: Calculate GridTypeTargetGroup / 10,100,1000,10000
AttributeCreator_4
    ATTR_TABLE = SET_TO GridTypeTargetGroup = FME_CONDITIONAL:DEFAULT_VALUE'1'BOOL_OP;OR;COMPOSITE_TEST;1;TEST @Value(DimGridTypeName) = 10m'10'BOOL_OP;OR;COMPOSITE_TEST;<Unused>;TEST @Value(DimGridTypeName) = 100m'100'BOOL_OP;OR;COMPOSITE_TEST;<Unused>;TEST @Value(DimGridTypeName) = 1km'1000'BOOL_OP;OR;COMPOSITE_TEST;<Unused>;TEST @Value(DimGridTypeName) = 10km'10000'FME_NUM_CONDITIONS5___
    -> Sorter
Note: Sort the scales
Sorter
    SORT_PARM = GridTypeTargetGroup NUMERIC ASCENDING
    SORTED -> AttributeCreator
Note: Get the next scale
AttributeCreator
    ATTR_TABLE:
      SET_TO GridTypeTargetGroupNext = @Value(feature[+1].GridTypeTargetGroup)
      SET_TO GridTypeTarget = FME_CONDITIONAL:DEFAULT_VALUE'_FME_NO_OP_'BOOL_OP;OR;COMPOSITE_TEST;1;TEST @Value(DimGridTypeName) = 1m'1'BOOL_OP;OR;COMPOSITE_TEST;1;TEST @Value(DimGridTypeName) = 10m'10'BOOL_OP;OR;COMPOSITE_TEST;1;TEST @Value(DimGridTypeName) = 100m'100'BOOL_OP;OR;COMPOSITE_TEST;1;TEST @Value(DimGridTypeName) = 1km'1000'BOOL_OP;OR;COMPOSITE_TEST;1;TEST @Value(DimGridTypeName) = 10km'10000'FME_NUM_CONDITIONS6___
    NUM_PRIOR_FEATURES = 0
    NUM_SUBSEQUENT_FEATURES = 1
    -> AttributeCreator_2
Note: Create "AddGridNumScale" function / that transforms the GridNum from / 100m -> 1km or / 100m -> 10km / 1km ->10km
AttributeCreator_2
    ATTR_TABLE:
      SET_TO AddGridNumScale = FME_CONDITIONAL:DEFAULT_VALUE'jedi_cubes.`@Value(G_TableName)_@Value(DimGridTypeName)`.GridNum'BOOL_OP;OR;COMPOSITE_TEST;1;TEST @Value(GridTypeTarget) = 10'(jedi_cubes.`@Value(G_TableName)_@Value(DimGridTypeName)`.GridNum & cast(-256  as bigint)) as GridNum,
        (jedi_cubes.`@Value(G_TableName)_@Value(DimGridTypeName)`.GridNum & cast(-65536 as bigint)) as GridNum100m,
        (jedi_cubes.`@Value(G_TableName)_@Value(DimGridTypeName)`.GridNum & cast(-16777216 as bigint)) as GridNum1km,
        'BOOL_OP;OR;COMPOSITE_TEST;1;TEST @Value(GridTypeTarget) = 100'(jedi_cubes.`@Value(G_TableName)_@Value(DimGridTypeName)`.GridNum & cast(-65536 as bigint)) as GridNum,
        (jedi_cubes.`@Value(G_TableName)_@Value(DimGridTypeName)`.GridNum & cast(-65536 as bigint)) as GridNum100m,
        (jedi_cubes.`@Value(G_TableName)_@Value(DimGridTypeName)`.GridNum & cast(-16777216  as bigint)) as GridNum1km,'BOOL_OP;AND;COMPOSITE_TEST;1;TEST @Value(GridTypeTarget) = 1000'(jedi_cubes.`@Value(G_TableName)_@Value(DimGridTypeName)`.GridNum & cast(-16777216 as bigint)) as gridnum,
        (jedi_cubes.`@Value(G_TableName)_@Value(DimGridTypeName)`.GridNum & cast(-16777216 as bigint)) as gridnum1km,'BOOL_OP;AND;COMPOSITE_TEST;1;TEST @Value(GridTypeTarget) = 10000'(jedi_cubes.`@Value(G_TableName)_@Value(DimGridTypeName)`.GridNum & cast(-4294967296 as bigint)) as GridNum,'FME_NUM_CONDITIONS5___
      SET_TO AddGridNumScaleGroupBy = FME_CONDITIONAL:DEFAULT_VALUE'jedi_cubes.`@Value(G_TableName)_@Value(DimGridTypeName)`.GridNum'BOOL_OP;OR;COMPOSITE_TEST;1;TEST @Value(GridTypeTarget) = 10'(jedi_cubes.`@Value(G_TableName)_@Value(DimGridTypeName)`.GridNum & cast(-256 as bigint)) ,
        (jedi_cubes.`@Value(G_TableName)_@Value(DimGridTypeName)`.GridNum & cast(-65536 as bigint)) ,
        (jedi_cubes.`@Value(G_TableName)_@Value(DimGridTypeName)`.GridNum & cast(-16777216 as bigint))
        'BOOL_OP;OR;COMPOSITE_TEST;1;TEST @Value(GridTypeTarget) = 100'(jedi_cubes.`@Value(G_TableName)_@Value(DimGridTypeName)`.GridNum & cast(-65536 as bigint)) ,
        (jedi_cubes.`@Value(G_TableName)_@Value(DimGridTypeName)`.GridNum & cast(-16777216  as bigint))'BOOL_OP;AND;COMPOSITE_TEST;1;TEST @Value(GridTypeTarget) = 1000'(jedi_cubes.`@Value(G_TableName)_@Value(DimGridTypeName)`.GridNum & cast(-16777216 as bigint))
        'BOOL_OP;AND;COMPOSITE_TEST;1;TEST @Value(GridTypeTarget) = 10000'(jedi_cubes.`@Value(G_TableName)_@Value(DimGridTypeName)`.GridNum & cast(-4294967296 as bigint)) 'FME_NUM_CONDITIONS5___
    -> AttributeKeeper
AttributeKeeper
    CREATE_BULK_MODE_FEATURES = NO
    KEEP_ATTRS = GridTypeTarget,AddGridNumScale,DimGridTypeName,AddGridNumScaleGroupBy
    -> FeatureMerger [SUPPLIER]
FeatureMerger
    ATTR_ACCUM_MODE = Merge Supplier
    ATTR_CONFLICT_RES = Use Requestor
    CLEANING_TOLERANCE = None
    IGNORE_NULLS = No
    JOIN_KEYS = @Value(DimGridTypeName) @Value(DimGridTypeName) AUTO
    MERGE_TYPE = Attributes Only
    PROCESS_DUPS = No
    REJECT_NULL_MISSING_KEYS = No
    SUPPLIERS_FIRST = No
    MERGED -> Output (output)
Output (output)

FME custom transformer ReplaceFieldsFromNoScale

Parameters:
- F_TABLENAME =
- LIST_ATTR =
- _SQLFIELDSHIGHTOLOW =
- _SQL_GROUPBY_FIELDS_HIGHTOLOW =
- _TOTALSCALESTOREMOVE =

Input (input)
    -> AttributeCreator
Note: Set Counter
AttributeCreator
    ATTR_TABLE = SET_TO _counter = 0
    -> ListIndexer
LoopAgain (input)
    -> ListIndexer
Note: Get value
ListIndexer
    INDEX = @Value(_counter)
    LIST_ATTR = $(LIST_ATTR)
    PREFIX = _removeScale
    -> ReplaceFields
ReplaceFields: StringReplacer
    CASE = NO
    FIND_TEXT = [`.+`,a-z,\,A-Z,_, ,\.,0-9,\-,|\(,\|),|\)]{0,}jedi_cubes.\`@Value(F_TableName)_@Value(_list{@Value(_counter)})\`.[`.+`,a-z,\,A-Z,_, ,\.,0-9,\-,|\(,\|),|\)]{1,}
    NO_MATCH = _FME_NO_OP_
    REGEXP = YES
    SRC_ATTRS = _SQL_GroupBy_Fields_HighToLow,_SQLFieldsHighToLow
    -> TestFilter_3
TestFilter_3
    DEFAULT_VALUE = NoMore
    TEST_LIST = "BOOL_OP,OR,COMPOSITE_TEST,""""""1"""""",TEST_CLAUSE,TEST @Value(_counter) < @Value(_TotalScalesToRemove)",MoreValues
    MoreValues -> ExpressionEvaluator
    NoMore -> AttributeTrimmer
AttributeTrimmer
    SRC_ATTRS = _SQLFieldsHighToLow
    TRIM_TO_NONE = Yes
    TRIM_TYPE = Right
    -> TestFilter
TestFilter
    DEFAULT_VALUE = NoEndsWithComma
    TEST_LIST = "BOOL_OP,OR,COMPOSITE_TEST,""""""1"""""",TEST_CLAUSE,CASE_INSENSITIVE_TEST @Value(_SQLFieldsHighToLow) ENDS_WITH ,",ENDS_WITH ,
    ENDS_WITH , -> RemoveLastComma
    NoEndsWithComma -> Output (output)
RemoveLastComma: AttributeCreator
    ATTR_TABLE = SET_TO _SQLFieldsHighToLow = @Left(@Value(_SQLFieldsHighToLow),@StringLength(@Value(_SQLFieldsHighToLow))-1)
    -> Output (output)
Output (output)
ExpressionEvaluator
    ACTION = Create New Attribute
    EXPRESSION = @Value(_counter)+1
    VAL_ATTR = _counter
    -> LoopAgain (output)
LoopAgain (output)

FME custom transformer SQLUnionList

Parameters:
- DIMGRIDTYPENAME =
- DatabaseOwner =
- FieldName =
- GROUP_BY =
- TableName =
- TargetAttribute =

Input_2 (input)
    -> StringSearcher
    -> FeatureMerger [REQUESTOR]
Note: TargetAttribute receiving the final result
StringSearcher
    CASE = no
    MATCHED_RESULT_ATTR = $(TargetAttribute)
    REGEXP = a
    STRING_TO_SEARCH = a
    MATCHED -> ParameterFetcher
ParameterFetcher
    ATTR_LIST = _FieldName $(FieldName) _TableName $(TableName) _TargetAttribute $(TargetAttribute) _DatabaseOwner $(DatabaseOwner)
    -> AttributeCreator_2
Note: Compile SQL syntax depending / on the informaton provided
AttributeCreator_2
    ATTR_TABLE = SET_TO __SQLFieldNames = SELECT @Value(_FieldName) FROM  @Value(_DatabaseOwner).`@Value(_TableName)`
    -> Aggregator_2
Note: Make field snippeds unqiue
Aggregator_2
    ACCUM_ATTRS_NAME = Use Attributes From One Feature
    AGGREGATE_TYPE = Homogeneous Collection (If Possible)
    GROUP_BY = __SQLFieldNames
    MODE = Geometry - Assemble One Level
    ORDERED = No
    SEP = "\nUNION\n"
    AGGREGATE -> Aggregator
Note: Combine them all together
Aggregator
    ACCUM_ATTRS_NAME = Use Attributes From One Feature
    AGGREGATE_TYPE = Homogeneous Collection (If Possible)
    CONCAT_ATTRS = __SQLFieldNames
    GROUP_BY = DimGridTypeName
    MODE = Geometry - Assemble One Level
    ORDERED = No
    SEP = "\n    UNION\n    "
    AGGREGATE -> PythonCaller
Note: Set to users attribute
PythonCaller
    PYTHONSOURCE:
      import fme
      import fmeobjects
      # Template Function interface:
      # When using this function, make sure its name is set as the value of
      # the 'Class or Function to Process Features' transformer parameter
      def processFeature(feature):
          pass

      # Template Class Interface:
      # When using this class, make sure its name is set as the value of
      # the 'Class or Function to Process Features' transformer parameter
      class FeatureProcessor(object):
          def __init__(self):
              pass
          def input(self,feature):
              #
              # Move the new value into the target attribute user has chosen.
              #
              TargetAttribute = feature.getAttribute("_TargetAttribute")
              SQLFieldNames = feature.getAttribute("__SQLFieldNames")
              feature.setAttribute(TargetAttribute,SQLFieldNames)
              self.pyoutput(feature)
          def close(self):
              pass
    PYTHONSYMBOL = FeatureProcessor
    -> AttributeRemover
AttributeRemover
    REMOVE_ATTRS = _DatabaseOwner,_TableName,_TargetAttribute,__SQLFieldNames,_FieldName,_FieldAlias
    -> FeatureMerger [SUPPLIER]
Note: Remap new value to all values
FeatureMerger
    ATTR_ACCUM_MODE = Merge Supplier
    ATTR_CONFLICT_RES = Use Requestor
    CLEANING_TOLERANCE = None
    GROUP_BY = $(GROUP_BY)
    IGNORE_NULLS = No
    JOIN_KEYS = 1 1 AUTO
    MERGE_TYPE = Attributes Only
    PROCESS_DUPS = No
    REJECT_NULL_MISSING_KEYS = No
    SUPPLIERS_FIRST = No
    MERGED -> Output_2 (output)
Output_2 (output)

FME custom transformer CreateTSQLScripts
Creates a CUBE from the configured attributes in JEDI.
This workspace generates a TSQL script that produces a flat tables from a number of dimensions based on the user configuration in JEDI.
This script produces two distinctive products.
1. A full scale version of the cube-table. (For example 100m, 1km or 10km cell size)
2. A aggregated version of the cube-table. This means that we sum the areaHa and group by all given attributes losing the cell identifier from the table. The result of this will be a fairly small table that can easily be exported and re-used.

Parameters:
- AGGREGATEFUNCTION =
- CUBEFIELDALIAS =
- CUBEID =
- C_TABLENAME =
- DIMGRIDSPACING =
- DIMGRIDTYPENAME =
- DimsPerGroup =
- FIELDNAME =
- F_TABLENAME =
- F_TABLENAMEA =
- F_TABLENAMEHIGHTOLOW =
- GRIDTYPENAME =
- G_TABLENAME =
- SQLDWTABLENAME =
- TMODE_NAME =
- TMODE_Name =

Note: -- / -- Remove table if existing [dbo].[G_LEAC18_18_11_2016_100m] / -- / if exists (select top 1 name from sysobjects where name = 'G_LEAC18_18_11_2016_100m' and xtype = 'U') / DROP TABLE [dbo].[G_LEAC18_18_11_2016_100m] / GO / -- / -- Generate a G-Table for every scale level / -- The G.Table contains all unique GridNum, used later to perform a join agains all dimensions / -- / CREATE TABLE [dbo].[G_LEAC18_18_11_2016_100m] / WITH / ( / DISTRIBUTION = HASH([GridNum10k]), / CLUSTERED COLUMNSTORE INDEX / ) / AS / SELECT DISTINCT GridNum,GridNum10km FROM [dbo].[D_A_CLC_00_57_20161115_100m] / UNION / SELECT DISTINCT GridNum,GridNum10km FROM [dbo].[D_A_CLC_90_56_20161115_100m]
Note: CREATE TABLE F_LEAC18_18_11_2016_1km / WITH / ( / DISTRIBUTION = HASH([GridNum]), / CLUSTERED COLUMNSTORE INDEX / ) / AS / SELECT / [G_LEAC18_18_11_2016_1km].[GridNum], / [D_EBK_2016_7_11_1km].[EBK1KM] as 'Elevation', / [D_NUTS_2016_7_12_1km].[NUTS3_code] as 'NUTS3_code', / [D_WFD_2016_7_11_1km].[WFD_RBDSU_f1v4] as 'WFD_RBDSU', / [D_CoastelZones_2016_7_11_1km].[Distance] as 'Distance' / FROM G_LEAC18_18_11_2016_1km / LEFT JOIN D_EBK_2016_7_11_1km / ON [G_LEAC18_18_11_2016_1km].[GridNum] = D_EBK_2016_7_11_1km.[GridNum] / LEFT JOIN D_NUTS_2016_7_12_1km / ON [G_LEAC18_18_11_2016_1km].[GridNum] = D_NUTS_2016_7_12_1km.[GridNum] / LEFT JOIN D_WFD_2016_7_11_1km / ON [G_LEAC18_18_11_2016_1km].[GridNum] = D_WFD_2016_7_11_1km.[GridNum] / LEFT JOIN D_CoastelZones_2016_7_11_1km / ON [G_LEAC18_18_11_2016_1km].[GridNum] = D_CoastelZones_2016_7_11_1km.[GridNum]
Input (input)
    -> SQLUnionList [Input_2]
StringSearcher
    CASE = no
    MATCHED_RESULT_ATTR = _first_match
    MATCHES_ATTR = LeftJoinList
    REGEXP = LEFT JOIN
    STRING_TO_SEARCH = @Value(F_TSQL_SCALE_LEFT_JOIN_PART)
    MATCHED -> ListElementCounter
ListElementCounter
    CNT_ATTR = NumParts
    LIST_NAME = LeftJoinList{}
    -> AttributeCreator_6
Note: Merge the different scale levels together on the most detailed scale. / 100m when 100m + 1km + 10km / 1km when 1km + 10km
AttributeCreator_3_OUTPUT_-__AttributeCreator_8: Junction
    -> SqlFieldNameCompiler_NoSizes_3
Note: CREATE TABLE F_LEAC18_18_11_2016_A / WITH / ( / DISTRIBUTION = HASH([GridNum]), / CLUSTERED COLUMNSTORE INDEX / ) / AS / SELECT / [F_LEAC18_18_11_2016_1km100m].[GridNum1km] as [GridNum], / [F_LEAC18_18_11_2016_1km100m].[CLC06], / [F_LEAC18_18_11_2016_1km100m].[CLC12], / [F_LEAC18_18_11_2016_1km100m].[CLC90], / [F_LEAC18_18_11_2016_1km100m].[CLC00], / [F_LEAC18_18_11_2016_1km100m].[Elevation], / [F_LEAC18_18_11_2016_1km100m].[NUTS3_code], / [F_LEAC18_18_11_2016_1km100m].[WFD_RBDSU], / [F_LEAC18_18_11_2016_1km100m].[Distance], / Sum( [F_LEAC18_18_11_2016_1km100m].[AreaHa]) as [AreaHa] / FROM F_LEAC18_18_11_2016_1km100m / GROUP BY / [F_LEAC18_18_11_2016_1km100m].[GridNum1km], / [F_LEAC18_18_11_2016_1km100m].[CLC06], / [F_LEAC18_18_11_2016_1km100m].[CLC12], / [F_LEAC18_18_11_2016_1km100m].[CLC90], / [F_LEAC18_18_11_2016_1km100m].[CLC00], / [F_LEAC18_18_11_2016_1km100m].[Elevation], / [F_LEAC18_18_11_2016_1km100m].[NUTS3_code], / [F_LEAC18_18_11_2016_1km100m].[WFD_RBDSU], / [F_LEAC18_18_11_2016_1km100m].[Distance]
SqlFieldNameCompiler_NoSizes_3: SQLFieldNameCompiler_NoSizes
    DatabaseOwner = jedi_cubes
    FieldAlias = @Value(CubeFieldAlias)
    FieldName = @Value(CubeFieldAlias)
    TableName = @Value(F_TableNameHighToLow)
    TargetAttribute = _SQLFieldsA
    TotalIndents = 1
    -> AssignModeIndex
AssignModeIndex
    CUBEFIELDALIAS = @Value(CubeFieldAlias)
    CUBEID = @Value(CubeId)
    DimsPerGroup = $(DimsPerGroup)
    F_TABLENAMEHIGHTOLOW = @Value(F_TableNameHighToLow)
    _AGGREGATEFUNCTION = @Value(_AggregateFunction)
    -> Python_RemoveLastComma_6
Note: Python_RemoveLastComma_2
Python_RemoveLastComma_6: PythonCaller
    NEW_ATTRIBUTES = NoModeFieldsGroupped
    PYTHONSOURCE:
      import fme
      import re
      import fmeobjects
      # Template Function interface:
      # When using this function, make sure its name is set as the value of
      # the 'Class or Function to Process Features' transformer parameter
      def processFeature(feature):
          pass

      # Template Class Interface:
      # When using this class, make sure its name is set as the value of
      # the 'Class or Function to Process Features' transformer parameter
      class FeatureProcessor(object):
          def __init__(self):
              pass
          def input(self,feature):
              self._fields= feature.getAttribute('NoModeFields')
              self._fields= self._fields.rstrip()

              if (self._fields.startswith(',')):
                  self._fields= self._fields[1:]
              if (self._fields.endswith(',')):
                  self._fields= self._fields[:-1]
              self._fields= re.sub(r"as\s+\`.+\`","",self._fields,flags=re.IGNORECASE)
              feature.setAttribute('NoModeFields',self._fields)
              self.pyoutput(feature)
          def close(self):
              pass
    PYTHONSYMBOL = FeatureProcessor
    -> AttributeRemover_2
AttributeRemover_2
    REMOVE_ATTRS = _count,_Join_Field_Name,_Join_Table_Name,_Join_Type,_Source_Field_Name,_Source_Table_Name,_SQDW_GroupBy_Fields_Scale,_SQLJoin,_SQLUnion,_TargetAttribute,_TotalIndents,_AddAfterField,_AggregateFunction
    -> BuildModeQuery
BuildModeQuery
    AddGridNums = Yes
    AggregateFunction = @Value(AggregateFunction)
    DatabaseOwner = jedi_cubes
    FieldName = @Value(CubeFieldAlias)
    NOMODEFIELDS = @Value(NoModeFields)
    NUMGROUPTABLEA = @Value(NumGroupTableA)
    TMODE_NAME = @Value(TMODE_Name)
    TableName = @Value(F_TableNameHighToLow)
    TargetAttribute = ModeSubQuery
    TotalIndents = 1
    -> AddFunctionGridNumToTarget_3
Note: Calculate hectars and GridNum conversion
Note: CREATE TABLE F_LEAC18_18_11_2016 / WITH / ( / DISTRIBUTION = HASH([GridNum]), / CLUSTERED COLUMNSTORE INDEX / ) / AS / SELECT / HASHBYTES('md5', / CONCAT( / [F_LEAC18_18_11_2016_1km].[Elevation],'|', / [F_LEAC18_18_11_2016_1km].[NUTS3_code],'|', / [F_LEAC18_18_11_2016_1km].[WFD_RBDSU],'|', / [F_LEAC18_18_11_2016_1km].[Distance],'|NORELATIONSHIP|' / ) / ) as 'RecordId', / [F_LEAC18_18_11_2016_A].[GridNum], / [F_LEAC18_18_11_2016_A].[CLC06], / [F_LEAC18_18_11_2016_A].[CLC12], / [F_LEAC18_18_11_2016_A].[CLC90], / [F_LEAC18_18_11_2016_A].[CLC00], / [F_LEAC18_18_11_2016_1km].[Elevation], / [F_LEAC18_18_11_2016_1km].[NUTS3_code], / [F_LEAC18_18_11_2016_1km].[WFD_RBDSU], / [F_LEAC18_18_11_2016_1km].[Distance], / [dbo].[GridNum2Lon]( [F_LEAC18_18_11_2016_1km].[GridNum] ) as [longitude], / [dbo].[GridNum2Lat]( [F_LEAC18_18_11_2016_1km].[GridNum] ) as [latitude], / 100 as [AreaHa] / FROM [F_LEAC18_18_11_2016_1km] / LEFT JOIN [F_LEAC18_18_11_2016_A] / ON [F_LEAC18_18_11_2016_1km].[GridNum] = [F_LEAC18_18_11_2016_A].[GridNum] / WHERE [F_LEAC18_18_11_2016_A].[GridNum] is NULL / UNION ALL / SELECT / HASHBYTES('md5', / CONCAT( / [F_LEAC18_18_11_2016_A].[CLC06],'|', / [F_LEAC18_18_11_2016_A].[CLC12],'|', / [F_LEAC18_18_11_2016_A].[CLC90],'|', / [F_LEAC18_18_11_2016_A].[CLC00],'|', / [F_LEAC18_18_11_2016_A].[Elevation],'|', / [F_LEAC18_18_11_2016_A].[NUTS3_code],'|', / [F_LEAC18_18_11_2016_A].[WFD_RBDSU],'|', / [F_LEAC18_18_11_2016_A].[Distance],'|' / ) / ) as 'RecordId', / [F_LEAC18_18_11_2016_A].[GridNum], / [F_LEAC18_18_11_2016_A].[CLC06], / [F_LEAC18_18_11_2016_A].[CLC12], / [F_LEAC18_18_11_2016_A].[CLC90], / [F_LEAC18_18_11_2016_A].[CLC00], / [F_LEAC18_18_11_2016_A].[Elevation], / [F_LEAC18_18_11_2016_A].[NUTS3_code], / [F_LEAC18_18_11_2016_A].[WFD_RBDSU], / [F_LEAC18_18_11_2016_A].[Distance], / [dbo].[GridNum2Lon]( [F_LEAC18_18_11_2016_A].[GridNum] ) as [longitude], / [dbo].[GridNum2Lat]( [F_LEAC18_18_11_2016_A].[GridNum] ) as [latitude], / [F_LEAC18_18_11_2016_A].[AreaHa] / FROM [F_LEAC18_18_11_2016_A]
AddFunctionGridNumToTarget_3
    DIMGRIDSPACING = @Value(DimGridSpacing)
    DIMGRIDTYPENAME = @Value(DimGridTypeName)
    GRIDTYPENAME = @Value(GridTypeName)
    TABLENAME = @Value(F_TableNameHighToLow)
    -> CreateTableAParts
CreateTableAParts
    ADDGRIDNUMSCALE = @Value(AddGridNumScale)
    CUBEID = @Value(CubeId)
    F_TABLENAMEA = @Value(F_TableNameA)
    F_TABLENAMEHIGHTOLOW = @Value(F_TableNameHighToLow)
    MODEFIELDS = @Value(ModeFields)
    MODESUBQUERY = @Value(ModeSubQuery)
    NOMODEFIELDS = @Value(NoModeFields)
    NUMGROUPTABLEA = @Value(NumGroupTableA)
    SQL_NOMODE = @Value(SQL_NoMode)
    _AGGREGATEFUNCTION = @Value(AggregateFunction)
    _FIELDALIAS = @Value(_FieldAlias)
    _FIELDNAME = @Value(_FieldName)
    -> AttributeRemover
AttributeRemover
    REMOVE_ATTRS = join_cond,ModeSubQuery,NoModeFields,NoModeFieldsAux,SQL_NoMode,T1GridNumCond,TAGridNumCond
    -> FeatureMerger [REQUESTOR]
Note: CREATE TABLE F_LEAC18_18_11_2016_HightToLow / WITH / ( / DISTRIBUTION = HASH([GridNum1km]), / CLUSTERED COLUMNSTORE INDEX / ) / AS / SELECT / [F_LEAC18_18_11_2016_100m].[GridNum], / [F_LEAC18_18_11_2016_100m].[GridNum1km], / [F_LEAC18_18_11_2016_100m].[CLC06], / [F_LEAC18_18_11_2016_100m].[CLC12], / [F_LEAC18_18_11_2016_100m].[CLC90], / [F_LEAC18_18_11_2016_100m].[CLC00], / [F_LEAC18_18_11_2016_1km].[Elevation], / [F_LEAC18_18_11_2016_1km].[NUTS3_code], / [F_LEAC18_18_11_2016_1km].[WFD_RBDSU], / [F_LEAC18_18_11_2016_1km].[Distance], / 1 as [AreaHa] / FROM F_LEAC18_18_11_2016_100m / LEFT JOIN F_LEAC18_18_11_2016_1km / ON F_LEAC18_18_11_2016_100m.[GridNum1km] = F_LEAC18_18_11_2016_1km.[GridNum]
SqlFieldNameCompiler_NoSizes: SQLFieldNameCompiler_NoSizes
    DatabaseOwner = jedi_cubes
    FieldAlias = @Value(CubeFieldAlias)
    FieldName = @Value(CubeFieldAlias)
    TableName = @Value(F_TableName)_@Value(DimGridTypeName)
    TargetAttribute = _SQLFieldsHighToLow
    TotalIndents = 2
    -> SqlFieldNameCompiler_NoSize2
SqlFieldNameCompiler_NoSize2: SQLFieldNameCompiler_NoSizes
    AggregateFunction = @Value(AggregateFunction)
    DatabaseOwner = jedi_cubes
    FieldAlias = @Value(CubeFieldAlias)
    FieldName = @Value(CubeFieldAlias)
    TableName = @Value(F_TableName)_@Value(DimGridTypeName)
    TargetAttribute = _SQL_Fields_HighToLow
    TotalIndents = 2
    -> AttributeCreator_16
AttributeCreator_16
    ATTR_TABLE = SET_TO _SQL_GroupBy_Fields_HighToLow = @Value(_SQL_Fields_HighToLow)
    -> StringReplacer_7
StringReplacer_7
    CASE = NO
    FIND_TEXT = (SUM|COUNT|AVG|MAX|MIN|STDEV|STDEVP|VAR|VARP|MODE)\([`.+`,a-z,\,A-Z,_, ,\.,0-9,\-,\(,\),\)]{1,}
    NO_MATCH = _FME_NO_OP_
    REGEXP = YES
    SRC_ATTRS = _SQL_GroupBy_Fields_HighToLow
    -> Python_RemoveLastComma_4
Python_RemoveLastComma_4: PythonCaller
    NEW_ATTRIBUTES = _SQLFTable_GroupByFields
    PYTHONSOURCE:
      import fme
      import fmeobjects
      # Template Function interface:
      # When using this function, make sure its name is set as the value of
      # the 'Class or Function to Process Features' transformer parameter
      def processFeature(feature):
          pass

      # Template Class Interface:
      # When using this class, make sure its name is set as the value of
      # the 'Class or Function to Process Features' transformer parameter
      class FeatureProcessor(object):
          def __init__(self):
              pass
          def input(self,feature):
              self._fields= feature.getAttribute('_SQL_GroupBy_Fields_HighToLow')
              self._fields= self._fields.rstrip()
              if (self._fields.endswith(',')):
                  self._fields= self._fields[:-1]
              self._fields= re.sub(r"as\s+\`.+\`","",self._fields,flags=re.IGNORECASE)
              feature.setAttribute('_SQL_GroupBy_Fields_HighToLow',self._fields)
              self.pyoutput(feature)
          def close(self):
              pass
    PYTHONSYMBOL = FeatureProcessor
    -> TestFilter_2
    -> FeatureJoiner_4 [LEFT]
TestFilter_2
    DEFAULT_VALUE = <UNFILTERED>
    TEST_LIST = "BOOL_OP,OR,COMPOSITE_TEST,""""""1"""""",TEST_CLAUSE,TEST _AggregateFunction NOT_ATTRIBUTE_HAS_A_VALUE """,!AGG
    !AGG -> AttributeCreator_8
AttributeCreator_8
    ATTR_TABLE = SET_TO PartitionFields = @Value(CubeFieldAlias)
    -> AttributeKeeper_6
Note: Remove last comma
AttributeKeeper_6
    CREATE_BULK_MODE_FEATURES = NO
    KEEP_ATTRS = CubeId,PartitionFields
    -> Aggregator_5
Aggregator_5
    ACCUM_ATTRS_NAME = Use Attributes From One Feature
    AGGREGATE_TYPE = Homogeneous Collection (If Possible)
    CONCAT_ATTRS = PartitionFields
    GROUP_BY = CubeId
    MODE = Geometry - Assemble One Level
    SEP = ,
    AGGREGATE -> AttributeCreator_9
AttributeCreator_9
    ATTR_TABLE = SET_TO PartitionFields = ,@Value(PartitionFields)
    -> FeatureJoiner_4 [RIGHT]
FeatureJoiner_4
    ATTR_CONFLICT_RES = Use Left
    GEOMETRY_HANDLING = Use Left
    GROUP_BY = CubeId
    JOIN_KEYS = CubeId CubeId AUTO
    JOIN_MODE = Left
    JOINED -> AttributeCreator_12
AttributeCreator_12
    ATTR_TABLE = SET_TO PartitionFields = FME_CONDITIONAL:DEFAULT_VALUE''BOOL_OP;OR;COMPOSITE_TEST;1;TEST PartitionFields ATTRIBUTE_HAS_A_VALUE _FME_BLANK_STRING_'@Value(PartitionFields)'FME_NUM_CONDITIONS2___
    -> GetFromTableName
Note: Aggregate and find the higest scale / and use it as FROM table. / Also join the _SQLFields together during the aggregate
GetFromTableName
    DIMGRIDSPACING = @Value(DimGridSpacing)
    DIMGRIDTYPENAME = @Value(DimGridTypeName)
    F_TABLENAME = @Value(F_TableName)
    GRIDTYPENAME = @Value(GridTypeName)
    GRIDTYPETARGET = @Value(GridTypeTarget)
    G_TABLENAME = @Value(G_TableName)
    _SQLFIELDSHIGHTOLOW = @Value(_SQL_Fields_HighToLow)
    _SQL_GROUPBY_FIELDS_HIGHTOLOW = @Value(_SQL_GroupBy_Fields_HighToLow)
    -> GroupByFields
Note: Create TSQL for F_TableTSQLHightToLow
AttributeCreator_7
    ATTR_TABLE:
      SET_TO F_TableTSQLHighToLow = FME_CONDITIONAL:DEFAULT_VALUE'drop table if exists jedi_cubes.`@Value(F_TableNameHighToLow)`;
        @Value(F_TableTSQLHighToLow)
        @Value(_SQL_GroupBy_Fields_HighToLow)
        'BOOL_OP;AND;COMPOSITE_TEST;1 AND 2;TEST @Value(_TotalGridTypes) = 1;TEST @Value(NumScales) = 0'drop table if exists jedi_cubes.`@Value(F_TableNameHighToLow)`;
        SELECT *,
        row_number()  OVER (PARTITION BY GridNum10Km, GridNum @Value(PartitionFields) ORDER BY areaHa)  as numrow
        FROM (
        SELECT
            jedi_cubes.`@Value(_FromHighToLow)`.`GridNum10km`,
            @Value(CastedGridNumForHighToLow),
            @Value(_SQLFieldsHighToLow),
            sum(areaHa) as areaHa
        FROM
            jedi_cubes.`@Value(_FromHighToLow)`
         GROUP BY
             jedi_cubes.`@Value(_FromHighToLow)`.`GridNum10km`,
            @ReplaceString(@Value(CastedGridNumForHighToLow), as GridNum,"")
            @Value(_SQL_GroupBy_Fields_HighToLow)
        )'BOOL_OP;AND;COMPOSITE_TEST;1 AND 2 AND 3;TEST @Value(_TotalGridTypes) > 1;TEST @Value(NumScales) > 0;TEST @Value(Last) = 1'drop table if exists jedi_cubes.`@Value(F_TableNameHighToLow)`;
        SELECT *,
        row_number()  OVER (PARTITION BY GridNum10Km, GridNum @Value(PartitionFields) ORDER BY areaHa)  as numrow
        FROM (
        @Value(F_TableTSQLHighToLow)
        @Value(_SQL_GroupBy_Fields_HighToLow)
        )'FME_NUM_CONDITIONS3___
    -> AttributeKeeper
AttributeKeeper
    CREATE_BULK_MODE_FEATURES = NO
    KEEP_ATTRS = F_TableTSQLHighToLow
    -> Aggregator
Aggregator
    ACCUM_ATTRS_NAME = Use Attributes From One Feature
    AGGREGATE_TYPE = Homogeneous Collection (If Possible)
    CONCAT_ATTRS = F_TableTSQLHighToLow
    MODE = Geometry - Assemble One Level
    SEP = ","
    AGGREGATE -> FeatureMerger [SUPPLIER]
Note: -- Remove table if existing [dbo].[C_LEAC18_18_11_2016] / if exists (select top 1 name from sysobjects where name = 'C_LEAC18_18_11_2016' and xtype = 'U') / DROP TABLE [dbo].[C_LEAC18_18_11_2016] / GO / -- / -- Produce final table including all attributes / -- / CREATE TABLE [dbo].[C_LEAC18_18_11_2016] / WITH / ( / DISTRIBUTION = HASH([RecordId]), / CLUSTERED COLUMNSTORE INDEX / ) / AS / SELECT / [dbo].[F_LEAC18_18_11_2016].[RecordId], / [dbo].[F_LEAC18_18_11_2016].[CLC90], / [dbo].[F_LEAC18_18_11_2016].[CLC00], / [dbo].[F_LEAC18_18_11_2016].[Pop_2006_GEOSTAT], / [dbo].[F_LEAC18_18_11_2016].[EuroBoundaryCode], / SUM([dbo].[F_LEAC18_18_11_2016].[AreaHa]) As [AreaHa] / FROM [dbo].[F_LEAC18_18_11_2016] / GROUP BY / [dbo].[F_LEAC18_18_11_2016].[RecordId], / [dbo].[F_LEAC18_18_11_2016].[CLC90], / [dbo].[F_LEAC18_18_11_2016].[CLC00], / [dbo].[F_LEAC18_18_11_2016].[Pop_2006_GEOSTAT], / [dbo].[F_LEAC18_18_11_2016].[EuroBoundaryCode] / GO / CREATE STATISTICS RecordId ON [dbo].[F_LEAC18_18_11_2016](RecordId)
Note: -- / -- Produce final table including all attributes / -- / CREATE TABLE [dbo].[M_LEAC18_18_11_2016] / WITH / ( / DISTRIBUTION = HASH([RecordId]), / CLUSTERED COLUMNSTORE INDEX / ) / AS / SELECT / [dbo].[F_LEAC18_18_11_2016].[RecordId], / [dbo].[F_LEAC18_18_11_2016].[GridNum], / [dbo].[F_LEAC18_18_11_2016].[longitude], / [dbo].[F_LEAC18_18_11_2016].[latitude] / FROM [dbo].[F_LEAC18_18_11_2016]
FeatureMerger
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> Counter
Note: CREATE TABLE [dbo].[CL_LEAC18_18_11_2016] / WITH / ( / CLUSTERED COLUMNSTORE INDEX, / DISTRIBUTION = HASH(RecordId) / --DISTRIBUTED = ROUND_ROBIN / ) / AS / SELECT / [dbo].[C_LEAC18_18_11_2016].[CLC90], / [dbo].[C_LEAC18_18_11_2016].[CLC00], / [dbo].[C_LEAC18_18_11_2016].[Pop_2006_GEOSTAT], / [dbo].[C_LEAC18_18_11_2016].[EuroBoundaryCode], / [dbo].[L_CLC_2017_12_8_1].[LEVEL3_CODE] as [CLC90 L3 Code], / [dbo].[L_CLC_2017_12_8_1].[LEVEL2_CODE] as [CLC90 L2 Code], / [dbo].[L_CLC_2017_12_8_1].[LEVEL1_CODE] as [CLC90 L1 Code], / [dbo].[L_CLC_2017_12_8_1].[LEVEL3_NAME] as [CLC90 L3 Name], / [dbo].[L_CLC_2017_12_8_1].[LEVEL2_NAME] as [CLC90 L2 Name], / [dbo].[L_CLC_2017_12_8_1].[LEVEL1_NAME] as [CLC90 L1 Name], / [dbo].[L_CLC_2017_12_8_2].[LEVEL3_CODE] as [CLC00 L3 Code], / [dbo].[L_CLC_2017_12_8_2].[LEVEL2_CODE] as [CLC00 L2 Code], / [dbo].[L_CLC_2017_12_8_2].[LEVEL1_CODE] as [CLC00 L1 Code], / [dbo].[L_CLC_2017_12_8_2].[LEVEL3_NAME] as [CLC00 L3 Name], / [dbo].[L_CLC_2017_12_8_2].[LEVEL2_NAME] as [CLC00 L2 Name], / [dbo].[L_CLC_2017_12_8_2].[LEVEL1_NAME] as [CLC00 L1 Name], / [dbo].[L_EuroBoundaryMapV5_2017_12_8_3].[ADM_ID] as [ADM_ID] , / [dbo].[C_LEAC18_18_11_2016].[AreaHa], / [dbo].[C_LEAC18_18_11_2016].[RecordId] / FROM [dbo].[C_LEAC18_18_11_2016] / LEFT JOIN [L_CLC_2017_12_8] AS L_CLC_2017_12_8_2 / ON [CL_LEAC18_18_11_2016].[CLC00] = CAST(L_CLC_2017_12_8_2.[LEVEL3_CODE] AS varchar(3)) / LEFT JOIN [L_CLC_2017_12_8] AS L_CLC_2017_12_8_1 / ON [CL_LEAC18_18_11_2016].[CLC90] = CAST(L_CLC_2017_12_8_1.[LEVEL3_CODE] AS smallint) / LEFT JOIN [L_EuroBoundaryMapV5_2017_12_8] AS L_EuroBoundaryMapV5_2017_12_8_3 / ON [CL_LEAC18_18_11_2016].[EuroBoundaryCode] = L_EuroBoundaryMapV5_2017_12_8_3.[ADM_ID]
Output (output)

Bookmark: G_<CUBENAME>_<Scale>
Note: Create select statement for UNION LIST
SQLUnionList
    DIMGRIDTYPENAME = @Value(DimGridTypeName)
    DatabaseOwner = jedi_dimensions
    FieldName = GridNum,GridNum10km
    GROUP_BY = DimGridTypeName
    TableName = @Value(SQLDWTableName)
    TargetAttribute = _SQLUnion
    Output_2 -> AttributeCreator_2
Note: Get all unique GridNum into one table per scale level. (100m, 1km, 10km
Note: Build T-SQL for / G_TableTSQL (Scale)
AttributeCreator_2
    ATTR_TABLE:
      SET_TO G_TableTSQL = drop table if exists jedi_cubes.`@Value(G_TableName)_@Value(DimGridTypeName)`;
        @Value(_SQLUnion)
    -> G_HighToLow
Note: Create select for joined high to low gridnums
G_HighToLow
    DIMGRIDTYPENAME = @Value(DimGridTypeName)
    GRIDTYPENAME = @Value(GridTypeName)
    G_TABLENAME = @Value(G_TableName)
    -> AttributeCreator_4
Note: Build T-SQL for / G_TableTSQL (Scale)
AttributeCreator_4
    ATTR_TABLE:
      SET_TO G_HighToLow_TSQL = FME_CONDITIONAL:DEFAULT_VALUE'FME_NULL_VALUE'BOOL_OP;OR;COMPOSITE_TEST;1;TEST @Value(G_HighToLowName) != @Value(G_TableName)_HighToLow_'drop table if exists jedi_cubes.`@Value(G_HighToLowName)`;@Value(G_HighToLowQuery)

        'FME_NUM_CONDITIONS2___
    -> SQLFieldNameCompiler

Bookmark: F_<CubeName>_<Scale>
Note: Combine all dimensions towards on single table for every scale level (100m, 1km, 10km) / The GridNum must be calculated so we join to higher scale with the lower scale. / Example: / 100m + 1km -> 100m (GridNum to 1km) -> 1km / 1km + 10km -> 1km (GridNum to 10km) -> 10km
SQLFieldNameCompiler
    DatabaseOwner = jedi_dimensions
    DimGridTypeName = @Value(DimGridTypeName)
    DimsPerGroup = $(DimsPerGroup)
    FieldAlias = @Value(CubeFieldAlias)
    FieldName = @Value(FieldName)
    TableName = @Value(SQLDWTableName)
    TargetAttribute = _SQLFields
    TotalIndents = 2
    -> F_GridNumCalculator
F_GridNumCalculator
    DIMGRIDTYPENAME = @Value(DimGridTypeName)
    G_TABLENAME = @Value(G_TableName)
    -> SQLJoinCompiler
SQLJoinCompiler
    DIMGRIDTYPENAME = @Value(DimGridTypeName)
    DatabaseOwner = jedi_dimensions
    DimsPerGroup = $(DimsPerGroup)
    Group_by = @Value(DimGridTypeName)
    Join_Field_Name = GridNum,GridNum10km
    Join_Table_Name = @Value(SQLDWTableName)
    Join_Type = LEFT
    Source_Field_Name = GridNum,GridNum10km
    Source_Table_Name = @Value(G_TableName)_@Value(DimGridTypeName)
    TargetAttribute = _SQLJoin
    TotalIndents = 2
    -> SQLFieldNameCompiler_12
Note: Create Aggregation fields
SQLFieldNameCompiler_12
    AggregateFunction = @Value(AggregateFunction)
    DatabaseOwner = jedi_dimensions
    DimGridTypeName = @Value(DimGridTypeName)
    DimsPerGroup = 7
    FieldAlias = @Value(CubeFieldAlias)
    FieldName = @Value(FieldName)
    TableName = @Value(SQLDWTableName)
    TargetAttribute = _SQDW_Fields_Scale
    TotalIndents = 2
    -> AttributeCreator_13
Note: Remove aggregate functions / from group by
AttributeCreator_13
    ATTR_TABLE = SET_TO _SQDW_GroupBy_Fields_Scale = @Value(_SQDW_Fields_Scale)
    -> StringReplacer_5
Note: Remove AGG and MODE fields
StringReplacer_5
    CASE = NO
    FIND_TEXT = (SUM|COUNT|AVG|MAX|MIN|STDEV|STDEVP|VAR|VARP|MODE)\([`.+`,a-z,\,A-Z,_, ,\.,0-9,\-,\(,\),\)]{1,}
    NO_MATCH = _FME_NO_OP_
    REGEXP = YES
    SRC_ATTRS = _SQDW_GroupBy_Fields_Scale
    -> Python_RemoveLastComma_3
Note: Python_RemoveLastComma_2
Python_RemoveLastComma_3: PythonCaller
    NEW_ATTRIBUTES = _SQLFTable_GroupByFields
    PYTHONSOURCE:
      import fme
      import re
      import fmeobjects
      # Template Function interface:
      # When using this function, make sure its name is set as the value of
      # the 'Class or Function to Process Features' transformer parameter
      def processFeature(feature):
          pass

      # Template Class Interface:
      # When using this class, make sure its name is set as the value of
      # the 'Class or Function to Process Features' transformer parameter
      class FeatureProcessor(object):
          def __init__(self):
              pass
          def input(self,feature):
              self._fields= feature.getAttribute('_SQDW_GroupBy_Fields_Scale')
              self._fields= self._fields.rstrip()

              if (self._fields.endswith(',')):
                  self._fields= self._fields[:-1]
              if (self._fields !=''):
                  self._fields = ',' + self._fields
              self._fields = re.sub(r"as\s+\`.+\`","",self._fields,flags=re.IGNORECASE)
              feature.setAttribute('_SQDW_GroupBy_Fields_Scale',self._fields)
              self.pyoutput(feature)
          def close(self):
              pass
    PYTHONSYMBOL = FeatureProcessor
    -> AttributeCreator_15
AttributeCreator_15
    ATTR_TABLE = SET_TO _SQDW_DimSize = FME_CONDITIONAL:DEFAULT_VALUE'0.0001'BOOL_OP;OR;COMPOSITE_TEST;1;TEST @Value(DimGridSpacing) = 10'0.01'BOOL_OP;OR;COMPOSITE_TEST;<Unused>;TEST @Value(DimGridSpacing) = 100'1'BOOL_OP;OR;COMPOSITE_TEST;<Unused>;TEST @Value(DimGridSpacing) = 1000'100'BOOL_OP;OR;COMPOSITE_TEST;<Unused>;TEST @Value(DimGridSpacing) = 10000'10000'FME_NUM_CONDITIONS5___
    -> AttributeCreator_3
Note: Create table for / F_TableTSQLScale
AttributeCreator_3
    ATTR_TABLE:
      SET_TO F_TableTSQLScale_Parts = drop table if exists jedi_cubes.`@Value(F_TableName)_@Value(DimGridTypeName)_@Value(NumGroup)`;
        SELECT
            @Value(G_TableName)_@Value(DimGridTypeName).GridNum10km,
        	@Value(AddGridNumScale)
        @Value(_SQDW_Fields_Scale)
        ,CAST(@Value(_SQDW_DimSize) as double) as AreaHa
        FROM  jedi_cubes.`@Value(G_TableName)_@Value(DimGridTypeName)`
        @Value(SQLJoin)
        GROUP BY
                jedi_cubes.`@Value(G_TableName)_@Value(DimGridTypeName)`.GridNum10km,
                @Value(AddGridNumScaleGroupBy)
        @Value(_SQDW_GroupBy_Fields_Scale)
    -> DuplicateFilter
    -> AttributeCreator_11
    -> Aggregator_2

Bookmark: Aggregate all the queries by Dimension Size
AttributeCreator_11
    ATTR_TABLE = SET_TO F_TableTSQLScale_Part = @Value(F_TableTSQLScale_Parts)
    -> FeatureJoiner [LEFT]
DuplicateFilter
    INPUT_ORDERED_CHOICE = No
    KEYATTR = F_TableTSQLScale_Parts GridTypeName NumGroup
    UNIQUE -> AttributeKeeper_2
    UNIQUE -> AttributeCreator_5
AttributeKeeper_2
    CREATE_BULK_MODE_FEATURES = NO
    KEEP_ATTRS = F_TableTSQLScale_Parts,DimGridTypeName
    -> Aggregator_3
Aggregator_3
    ACCUM_ATTRS_NAME = Use Attributes From One Feature
    AGGREGATE_TYPE = Homogeneous Collection (If Possible)
    CONCAT_ATTRS = F_TableTSQLScale_Parts
    GROUP_BY = DimGridTypeName
    MODE = Geometry - Assemble One Level
    SEP = ","
    AGGREGATE -> FeatureJoiner [RIGHT]
FeatureJoiner
    ATTR_CONFLICT_RES = Use Right
    GEOMETRY_HANDLING = Use Left
    JOIN_KEYS = DimGridTypeName DimGridTypeName AUTO
    JOIN_MODE = Left
    JOINED -> FeatureJoiner_3 [LEFT]
AttributeCreator_5
    ATTR_TABLE:
      SET_TO F_TSQL_SCALE_LEFT_JOIN_PART =     LEFT JOIN jedi_cubes.`@Value(F_TableName)_@Value(DimGridTypeName)_@Value(NumGroup)`
                ON       jedi_cubes.`@Value(F_TableName)_@Value(DimGridTypeName)_@Value(NumGroup)`.`GridNum` = jedi_cubes.`@Value(G_TableName)_@Value(DimGridTypeName)`.`GridNum`
            AND
                jedi_cubes.`@Value(F_TableName)_@Value(DimGridTypeName)_@Value(NumGroup)`.`GridNum10km` = jedi_cubes.`@Value(G_TableName)_@Value(DimGridTypeName)`.`GridNum10km`
    -> AttributeKeeper_4
AttributeKeeper_4
    CREATE_BULK_MODE_FEATURES = NO
    KEEP_ATTRS = DimGridTypeName,F_TSQL_SCALE_LEFT_JOIN_PART,AddGridNumScale,AddGridNumScaleGroupBy,NumGroup
    -> Aggregator_4
Aggregator_4
    ACCUM_ATTRS_NAME = Use Attributes From One Feature
    AGGREGATE_TYPE = Homogeneous Collection (If Possible)
    CONCAT_ATTRS = F_TSQL_SCALE_LEFT_JOIN_PART
    GROUP_BY = DimGridTypeName
    MODE = Geometry - Assemble One Level
    SEP = "\n"
    AGGREGATE -> FeatureJoiner_2 [LEFT]
Aggregator_2
    ACCUM_ATTRS_NAME = Use Attributes From One Feature
    AGGREGATE_TYPE = Homogeneous Collection (If Possible)
    CONCAT_ATTRS = CubeFieldAlias
    GROUP_BY = DimGridTypeName
    MODE = Geometry - Assemble One Level
    SEP = ",\n"
    AGGREGATE -> AttributeKeeper_3
AttributeKeeper_3
    CREATE_BULK_MODE_FEATURES = NO
    KEEP_ATTRS = CubeFieldAlias,DimGridTypeName,G_TableName,F_TableName,NumGroup
    -> FeatureJoiner_2 [RIGHT]
FeatureJoiner_2
    ATTR_CONFLICT_RES = Use Left
    GEOMETRY_HANDLING = Use Left
    JOIN_KEYS = DimGridTypeName DimGridTypeName AUTO
    JOIN_MODE = Inner
    JOINED -> AttributeCreator_14
AttributeCreator_14
    ATTR_TABLE = SET_TO AreaHa = FME_CONDITIONAL:DEFAULT_VALUE'_FME_NO_OP_'BOOL_OP;OR;COMPOSITE_TEST;1;TEST @Value(DimGridTypeName) = 10m'CAST(0.01 as double) as AreaHa,'BOOL_OP;OR;COMPOSITE_TEST;1;TEST @Value(DimGridTypeName) = 100m'CAST(1 as double) as AreaHa,'BOOL_OP;OR;COMPOSITE_TEST;1;TEST @Value(DimGridTypeName) = 1km'CAST(100 as double) as AreaHa,'BOOL_OP;OR;COMPOSITE_TEST;1;TEST @Value(DimGridTypeName) = 10km'CAST(10000 as double) as AreaHa,'FME_NUM_CONDITIONS5___
    -> AttributeCreator_6 [off]
    -> StringSearcher
Note: RENAME if only 1 part
AttributeCreator_6
    ATTR_TABLE:
      SET_TO F_TableTSQLScale = FME_CONDITIONAL:DEFAULT_VALUE'DROP TABLE IF EXISTS  jedi_cubes.`@Value(F_TableName)_@Value(DimGridTypeName)`;
        ALTER TABLE  jedi_cubes.`@Value(F_TableName)_@Value(DimGridTypeName)_@Value(NumGroup)` RENAME TO  jedi_cubes.`@Value(F_TableName)_@Value(DimGridTypeName)`;'BOOL_OP;OR;COMPOSITE_TEST;1;TEST @Value(NumParts) > 1'DROP TABLE IF EXISTS  jedi_cubes.`@Value(F_TableName)_@Value(DimGridTypeName)`;
        SELECT
            jedi_cubes.`@Value(G_TableName)_@Value(DimGridTypeName)`.`GridNum10km`,
            @Value(AddGridNumScale)
            @Value(AreaHa)
            @Value(CubeFieldAlias)
        FROM
         jedi_cubes.`@Value(G_TableName)_@Value(DimGridTypeName)`
         @Value(F_TSQL_SCALE_LEFT_JOIN_PART)'FME_NUM_CONDITIONS2___
    -> AttributeKeeper_5
AttributeKeeper_5
    CREATE_BULK_MODE_FEATURES = NO
    KEEP_ATTRS = DimGridTypeName,F_TableTSQLScale
    -> FeatureJoiner_3 [RIGHT]
FeatureJoiner_3
    ATTR_CONFLICT_RES = Use Left
    GEOMETRY_HANDLING = Use Left
    JOIN_KEYS = DimGridTypeName DimGridTypeName AUTO
    JOIN_MODE = Inner
    JOINED -> AttributeCreator_3_OUTPUT_-__AttributeCreator_8
    JOINED -> SqlFieldNameCompiler_NoSizes

Bookmark: Create the GROUP BY clause
GroupByFields: TestFilter
    DEFAULT_VALUE = NoGroupBy
    TEST_LIST = "BOOL_OP,OR,COMPOSITE_TEST,""""""1"""""",TEST_CLAUSE,TEST _SQL_GroupBy_Fields_HighToLow ATTRIBUTE_HAS_A_VALUE """,GroupBy
    GroupBy -> PreppendComma
    NoGroupBy -> CastedGridNumForHighToLow
PreppendComma: AttributeCreator
    ATTR_TABLE = SET_TO _SQL_GroupBy_Fields_HighToLow = ,@Value(_SQL_GroupBy_Fields_HighToLow)
    -> AttributeTrimmer
AttributeTrimmer
    SRC_ATTRS = _SQL_GroupBy_Fields_HighToLow
    TRIM_TO_NONE = Yes
    TRIM_TYPE = Right
    -> TestFilter
TestFilter
    DEFAULT_VALUE = NoEndsWithComma
    TEST_LIST = "BOOL_OP,OR,COMPOSITE_TEST,""""""1"""""",TEST_CLAUSE,CASE_INSENSITIVE_TEST @Value(_SQL_GroupBy_Fields_HighToLow) ENDS_WITH ,",ENDS_WITH ,
    ENDS_WITH , -> RemoveLastComma
    NoEndsWithComma -> CastedGridNumForHighToLow
RemoveLastComma: AttributeCreator
    ATTR_TABLE = SET_TO _SQL_GroupBy_Fields_HighToLow = @Left(@Value(_SQL_GroupBy_Fields_HighToLow),@StringLength(@Value(_SQL_GroupBy_Fields_HighToLow))-1)
    -> CastedGridNumForHighToLow
CastedGridNumForHighToLow: AttributeCreator
    ATTR_TABLE = SET_TO CastedGridNumForHighToLow = FME_CONDITIONAL:DEFAULT_VALUE'_FME_NO_OP_'BOOL_OP;OR;COMPOSITE_TEST;1;TEST @Value(GridTypeTarget) = 10'(jedi_cubes.`@Value(F_TableName)_@Value(DimGridTypeName)`.GridNum & cast(-256 as bigint)) as GridNum'BOOL_OP;OR;COMPOSITE_TEST;1;TEST @Value(GridTypeTarget) = 100'(jedi_cubes.`@Value(F_TableName)_@Value(DimGridTypeName)`.GridNum & cast(-65536 as bigint)) as GridNum'BOOL_OP;OR;COMPOSITE_TEST;1;TEST @Value(GridTypeTarget) = 1000'(jedi_cubes.`@Value(F_TableName)_@Value(DimGridTypeName)`.GridNum & cast(-16777216 as bigint)) as GridNum'BOOL_OP;OR;COMPOSITE_TEST;1;TEST @Value(GridTypeTarget) = 10000'(jedi_cubes.`@Value(F_TableName)_@Value(DimGridTypeName)`.GridNum & cast(-4294967296 as bigint)) as GridNum'FME_NUM_CONDITIONS5___
    -> AttributeCreator_7

Bookmark: F_<CUBENAME>
Counter
    CNT_ATTR = _preserveOrder
    DOMAIN = preserveordercounter
    SCOPE = Local
    START = 1
    -> SqlFieldNameCompiler_NoSizes_4
Note: Compile HASH for F_<Table>_<Date>_A / _SQLTableA_FieldsHash
SqlFieldNameCompiler_NoSizes_4: SQLFieldNameCompiler_NoSizes
    AddAfterField = ,'|'
    DatabaseOwner = jedi_cubes
    FieldAlias = @Value(CubeFieldAlias)
    FieldName = @Value(CubeFieldAlias)
    TableName = @Value(F_TableNameA)
    TargetAttribute = _SQLTableA_FieldsHash
    TotalIndents = 1
    -> SqlFieldNameCompiler_NoSizes_5
Note: Compile Fields for F_<Table>_<Date>_A / _SQLTableA_Fields
SqlFieldNameCompiler_NoSizes_5: SQLFieldNameCompiler_NoSizes
    DatabaseOwner = jedi_cubes
    FieldAlias = @Value(CubeFieldAlias)
    FieldName = @Value(CubeFieldAlias)
    TableName = @Value(F_TableNameA)
    TargetAttribute = _SQLTableA_Fields
    TotalIndents = 2
    -> AttributeCreator_17
AttributeCreator_17
    ATTR_TABLE:
      SET_TO _F_TableTSQL_Part1
      SET_TO AllTableAFields = @ReplaceString(@LowerCase(@Value(_SQLFieldsA))  ,@LowerCase(@Value(F_TableNameHighToLow)),@Value(F_TableNameA))
    -> AttributeCreator_10
Note: Concatinate the records form the most detailed scale with the records that did not match any GridNum in the most detailed levl
Note: Compile the full T-SQL / F_TableTSQL
AttributeCreator_10
    ATTR_TABLE:
      SET_TO F_TableTSQL = drop table if exists jedi_cubes.`@Value(F_TableName)`;
        @Value(_F_TableTSQL_Part1)

        SELECT
                jedi_cubes.`@Value(F_TableNameA)`.GridNum10km,
        		jedi_cubes.`@Value(F_TableNameA)`.GridNum,
        @Value(AllTableAFields),

        		GridNum2Lon(`@Value(F_TableNameA)`.GridNum ) as longitude,
        		GridNum2Lat(`@Value(F_TableNameA)`.GridNum) as latitude,

        		`@Value(F_TableNameA)`.AreaHa
        FROM jedi_cubes.`@Value(F_TableNameA)`
    -> SQLModeFieldNameCompiler_CTable

Bookmark: C_<TableName>_<Date>
SQLModeFieldNameCompiler_CTable
    AggregateFunction = @Value(AggregateFunction)
    DatabaseOwner = jedi_cubes
    FieldAlias = @Value(CubeFieldAlias)
    FieldName = @Value(CubeFieldAlias)
    Include_Agg = Yes
    TableName = @Value(F_TableName)
    TargetAttribute = SQL_NoModecube
    TotalIndents = 1
    -> NoModeFields_2
NoModeFields_2: AttributeCreator
    ATTR_TABLE = SET_TO NoModeFieldsCube = @Value(SQL_NoModecube)
    -> StringReplacer
StringReplacer
    CASE = NO
    FIND_TEXT = \(`TMODE_[`.+`,a-z,\,A-Z,_, ,\.,0-9,\-,\(,\),\)]{1,}
    NO_MATCH = _FME_NO_OP_
    REGEXP = YES
    SRC_ATTRS = NoModeFieldsCube
    -> ReplaceTMode_2
ReplaceTMode_2: StringReplacer
    CASE = NO
    FIND_TEXT = (SUM|COUNT|AVG|MAX|MIN|STDEV|STDEVP|VAR|VARP|MODE)\([`.+`,a-z,\,A-Z,_, ,\.,0-9,\-,\(,\),\)]{1,}
    NO_MATCH = _FME_NO_OP_
    REGEXP = YES
    SRC_ATTRS = NoModeFieldsCube
    -> Python_RemoveLastComma_5
Note: Python_RemoveLastComma_2
Python_RemoveLastComma_5: PythonCaller
    NEW_ATTRIBUTES = NoModeFieldsCube
    PYTHONSOURCE:
      import fme
      import re
      import fmeobjects
      # Template Function interface:
      # When using this function, make sure its name is set as the value of
      # the 'Class or Function to Process Features' transformer parameter
      def processFeature(feature):
          pass

      # Template Class Interface:
      # When using this class, make sure its name is set as the value of
      # the 'Class or Function to Process Features' transformer parameter
      class FeatureProcessor(object):
          def __init__(self):
              pass
          def input(self,feature):
              self._fields= feature.getAttribute('NoModeFieldsCube')
              self._fields= self._fields.rstrip()

              if (self._fields.startswith(',')):
                  self._fields= self._fields[1:]
              if (self._fields.endswith(',')):
                  self._fields= self._fields[:-1]
              self._fields= re.sub(r"as\s+\`.+\`","",self._fields,flags=re.IGNORECASE)
              feature.setAttribute('NoModeFieldsCube',self._fields)
              self.pyoutput(feature)
          def close(self):
              pass
    PYTHONSYMBOL = FeatureProcessor
    -> BuildCTableModeQuery [Input_2]
Note: Create MODE statements for C Table
BuildCTableModeQuery
    AddGridNums = No
    AggregateFunction = @Value(AggregateFunction)
    FieldName = @Value(CubeFieldAlias)
    NOMODEFIELDS = @Value(NoModeFieldsCube)
    TMODE_NAME = @Value(TMODE_Name)
    TableName = @Value(F_TableName)
    TargetAttribute = SQLFields
    TotalIndents = 1
    Output_2 -> AttributeCreator_20
AttributeCreator_20
    ATTR_TABLE = SET_TO _SQDW_GroupBy_Fields = @Value(SQL_NoModecube)
    -> RemoveAGGFormulas
RemoveAGGFormulas: StringReplacer
    CASE = NO
    FIND_TEXT = (SUM|COUNT|AVG|MAX|MIN|STDEV|STDEVP|VAR|VARP|MODE)\([`.+`,a-z,\,A-Z,_, ,\.,0-9,\-,\(,\),\)]{1,}
    NO_MATCH = _FME_NO_OP_
    REGEXP = YES
    SRC_ATTRS = _SQDW_GroupBy_Fields
    -> Python_CommasRemover
Python_CommasRemover: PythonCaller
    NEW_ATTRIBUTES = _SQDW_GroupBy_Fields
    PYTHONSOURCE:
      import fme
      import re
      import fmeobjects
      # Template Function interface:
      # When using this function, make sure its name is set as the value of
      # the 'Class or Function to Process Features' transformer parameter
      def processFeature(feature):
          pass

      # Template Class Interface:
      # When using this class, make sure its name is set as the value of
      # the 'Class or Function to Process Features' transformer parameter
      class FeatureProcessor(object):
          def __init__(self):
              pass
          def input(self,feature):
              self._fields= feature.getAttribute('_SQDW_GroupBy_Fields')
              self._fields= self._fields.rstrip()

              if (self._fields.startswith(',')):
                  self._fields= self._fields[1:]

              if (self._fields.endswith(',')):
                  self._fields= self._fields[:-1]

              self._fields =re.sub(r"as\s+\`.+\`","",self._fields,flags=re.IGNORECASE)
              feature.setAttribute('_SQDW_GroupBy_Fields',self._fields)
              self.pyoutput(feature)
          def close(self):
              pass
    PYTHONSYMBOL = FeatureProcessor
    -> StringSearcher_3
BuildCTableFields
    F_TABLENAME = @Value(F_TableName)
    TMODE_NAME = @Value(TMODE_Name)
    _AGGREGATEFUNCTION = @Value(_AggregateFunction)
    _FIELDALIAS = @Value(_FieldAlias)
    -> StringReplacer_2
StringReplacer_2
    CASE = NO
    FIND_TEXT = TMODE
    NO_MATCH = _FME_NO_OP_
    REGEXP = NO
    REPLACE_TEXT = @Value(TMODE_Name)_C
    SRC_ATTRS = _SQDW_GroupBy_Fields
    -> BuildCTable_SQL
Note: Compile the full T-SQL / C_TableTSQL
BuildCTable_SQL: AttributeCreator
    ATTR_TABLE:
      SET_TO C_TableTSQL = drop table if exists jedi_cubes.`@Value(C_TableName)`;
        SELECT
                @Value(CTable_Fields),
        SUM((jedi_cubes.`@Value(F_TableName)`.`AreaHa`) ) As AreaHa
        FROM jedi_cubes.`@Value(F_TableName)`
            @Value(ModeSubQueryCube)
        @Value(_SQDW_GroupBy_Fields)

      SET_TO C_TableTSQL_MODEs = @Value(CachedModeSubQueryCTable)
    -> ReplaceAVG_function
Note: Replace AVG with SUm(fied * areaHA)/sum(areaHa)
ReplaceAVG_function: PythonCaller
    PYTHONSOURCE:
      import fme
      import fmeobjects
      import re
      # Template Function interface:
      # When using this function, make sure its name is set as the value of
      # the 'Class or Function to Process Features' transformer parameter
      def processFeature(feature):
          pass

      # Template Class Interface:
      # When using this class, make sure its name is set as the value of
      # the 'Class or Function to Process Features' transformer parameter
      class FeatureProcessor(object):
          def __init__(self):
              pass
          def input(self,feature):
              self._fields= feature.getAttribute('C_TableTSQL')

              self._fields =re.sub(r"AVG\(([^)]+)\)","SUM(\g<1> * areaHa)/sum(areaHa)",self._fields,flags=re.IGNORECASE)
              feature.setAttribute('C_TableTSQL',self._fields)
              self.pyoutput(feature)

          def close(self):
              pass
    PYTHONSYMBOL = FeatureProcessor
    -> Add_GridTypeName
Add_GridTypeName: AttributeCreator
    ATTR_TABLE = SET_TO DimGridTypeName = @Value(_GROUP_BY)
    -> Output (output)

Bookmark: Create the GROUP BY clause
StringSearcher_3
    CASE = no
    MATCHED_RESULT_ATTR = _first_match
    REGEXP = (SUM|COUNT|AVG|MAX|MIN|STDEV|STDEVP|VAR|VARP|MODE)\([`.+`,a-z,\,A-Z,_, ,\.,0-9,\-,\(,\),\)]{1,}
    STRING_TO_SEARCH = @Value(SQL_NoModecube)
    MATCHED -> AttributeCreator_22
    NOT_MATCHED -> AttributeCreator_21
AttributeCreator_22
    ATTR_TABLE:
      SET_TO _SQDW_GroupBy_Fields = FME_CONDITIONAL:DEFAULT_VALUE'_FME_NO_OP_'BOOL_OP;OR;COMPOSITE_TEST;1;TEST NoModeFieldsCube NOT_ATTRIBUTE_HAS_A_VALUE _FME_BLANK_STRING_''BOOL_OP;OR;COMPOSITE_TEST;1;TEST _SQDW_GroupBy_Fields ATTRIBUTE_HAS_A_VALUE _FME_BLANK_STRING_'GROUP BY
           @Value(_SQDW_GroupBy_Fields)'FME_NUM_CONDITIONS3___
    -> BuildCTableFields
AttributeCreator_21
    ATTR_TABLE:
      SET_TO _SQDW_GroupBy_Fields = FME_CONDITIONAL:DEFAULT_VALUE'_FME_NO_OP_'BOOL_OP;OR;COMPOSITE_TEST;1;TEST NoModeFieldsCube NOT_ATTRIBUTE_HAS_A_VALUE _FME_BLANK_STRING_''BOOL_OP;OR;COMPOSITE_TEST;1;TEST _SQDW_GroupBy_Fields ATTRIBUTE_HAS_A_VALUE _FME_BLANK_STRING_'GROUP BY
           @Value(_SQDW_GroupBy_Fields)'FME_NUM_CONDITIONS3___
    -> BuildCTableFields

Bookmark: Buiid Partition By fields
AttributeCreator
    ATTR_TABLE:
      SET_TO SQL_Partition = @LowerCase(@Value(_SQL_GroupBy_Fields_HighToLow))
      SET_TO F_TableName = @LowerCase(@Value(F_TableName))
      SET_TO F_TableNameHighToLow = @LowerCase(@Value(F_TableNameHighToLow))
    -> StringReplacer_3
StringReplacer_3
    CASE = NO
    FIND_TEXT = jedi_cubes.`@Value(F_TableNameHighToLow)_@Value(PreviousScale)`.
    NO_MATCH = _FME_NO_OP_
    REGEXP = NO
    SRC_ATTRS = SQL_Partition
    -> StringReplacer_4
StringReplacer_4
    CASE = NO
    FIND_TEXT = jedi_cubes.`@Value(F_TableName)_@Value(_GROUP_BY)`.
    NO_MATCH = _FME_NO_OP_
    REGEXP = NO
    SRC_ATTRS = SQL_Partition

FME custom transformer AssignModeIndex

Parameters:
- CUBEFIELDALIAS =
- CUBEID =
- DimsPerGroup =
- F_TABLENAMEHIGHTOLOW =
- _AGGREGATEFUNCTION =

Input (input)
    -> SQLExecutor [INITIATOR]
SQLExecutor
    COMBINE_ATTRS = Result Attributes Only
    COMBINE_GEOM = Initiator Geometry Only
    DATASET = CubeManager
    EXPOSED_ATTRIBUTE_LIST = NumModes
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = CubeManager
    MSSQL_ADO_QUERY_FEATURE_TYPES_FOR_MERGE_FILTERS = Yes
    SQL_STATEMENT:
      SELECT count(aggregatefunction) as NumModes
        FROM [CubeManager].[dbo].[CubeFields]
      where cubeid = @Value(CubeId) and AggregateFunction ='MODE'
    RESULT -> FeatureMerger [SUPPLIER]
    INITIATOR -> FeatureMerger [REQUESTOR]
FeatureMerger
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> TestFilter
    MERGED -> FeatureJoiner_2 [LEFT]
TestFilter
    DEFAULT_VALUE = MODE
    TEST_LIST:
      "BOOL_OP,OR,COMPOSITE_TEST,""""""1"""""",TEST_CLAUSE,TEST _AggregateFunction NOT_ATTRIBUTE_HAS_A_VALUE """,NoAgg,"BOOL_OP,AND,COMPOSITE_TEST,""""""1 AND 2"""""",TEST_CLAUSE,TEST _AggregateFunction ATTRIBUTE_HAS_A_VALUE ""
      TEST @Value(_AggregateFunction) != MODE",Agg
    NoAgg -> AttributeCreator
    Agg -> AttributeCreator
    MODE -> Counter
AttributeCreator
    ATTR_TABLE = SET_TO SQL_NoMode = FME_CONDITIONAL:DEFAULT_VALUE''BOOL_OP;AND;COMPOSITE_TEST;1 AND 2;TEST _AggregateFunction ATTRIBUTE_HAS_A_VALUE _FME_BLANK_STRING_;TEST @Value(_AggregateFunction) != MODE'@Value(_AggregateFunction)(jedi_cubes.@Value(F_TableNameHighToLow).@Value(CubeFieldAlias)) as @Value(CubeFieldAlias)'BOOL_OP;AND;COMPOSITE_TEST;1;TEST _AggregateFunction NOT_ATTRIBUTE_HAS_A_VALUE _FME_BLANK_STRING_'jedi_cubes.@Value(F_TableNameHighToLow).@Value(CubeFieldAlias)'FME_NUM_CONDITIONS3___
    -> Aggregator_7
Aggregator_7
    ACCUM_ATTRS_NAME = Use Attributes From One Feature
    AGGREGATE_TYPE = Homogeneous Collection (If Possible)
    CONCAT_ATTRS = SQL_NoMode
    MODE = Geometry - Assemble One Level
    SEP = "\n,"
    AGGREGATE -> AttributeCreator_8
AttributeCreator_8
    ATTR_TABLE = SET_TO NoModeFields = @Value(SQL_NoMode)
    -> ReplaceTMode_And_AGG_2
ReplaceTMode_And_AGG_2: StringReplacer
    CASE = NO
    FIND_TEXT = (SUM|COUNT|AVG|MAX|MIN|STDEV|STDEVP|VAR|VARP|MODE)\([`.+`,a-z,\,A-Z,_, ,\.,0-9,\-,\(,\),\)]{1,}
    NO_MATCH = _FME_NO_OP_
    REGEXP = YES
    SRC_ATTRS = NoModeFields
    -> StringReplacer_3
StringReplacer_3
    CASE = NO
    FIND_TEXT = ,$
    NO_MATCH = _FME_NO_OP_
    REGEXP = YES
    SRC_ATTRS = NoModeFields,SQL_NoMode
    -> FeatureJoiner_2 [RIGHT]
FeatureJoiner_2
    ATTR_CONFLICT_RES = Use Left
    GEOMETRY_HANDLING = Use Left
    JOIN_KEYS = CubeId CubeId AUTO
    JOIN_MODE = Left
    JOINED -> Tester
Tester
    BOOL_OP = OR
    COMPOSITE_TEST = 1
    TEST_CLAUSE = TEST @Value(NumModes) = 0
    TEST_MODE = TEST
    PASSED -> RemoveWhiteLines
    FAILED -> FeatureJoiner_3 [LEFT]
Counter
    CNT_ATTR = NumMode
    DOMAIN = counter
    SCOPE = Global
    START = 0
    -> AttributeRemover_2
AttributeRemover_2
    REMOVE_ATTRS = _AggregateFunction,F_TableNameHighToLow
    -> FeatureJoiner_3 [RIGHT]
FeatureJoiner_3
    ATTR_CONFLICT_RES = Use Left
    GEOMETRY_HANDLING = Use Left
    JOIN_KEYS = CubeId CubeId AUTO CubeFieldAlias CubeFieldAlias AUTO
    JOIN_MODE = Left
    JOINED -> RemoveWhiteLines
RemoveWhiteLines: PythonCaller
    PYTHONSOURCE:
      import fme
      import fmeobjects
      import re
      # Template Function interface:
      # When using this function, make sure its name is set as the value of
      # the 'Class or Function to Process Features' transformer parameter
      def processFeature(feature):
          pass

      # Template Class Interface:
      # When using this class, make sure its name is set as the value of
      # the 'Class or Function to Process Features' transformer parameter
      class FeatureProcessor(object):
          def __init__(self):
              pass

          def input(self,feature):
              sqlNoMode= feature.getAttribute('SQL_NoMode')
              if (sqlNoMode!=""):
                  sqlNoMode = "\n".join([ll.rstrip() for ll in sqlNoMode.splitlines() if ll.strip()])
                  sqlNoMode = sqlNoMode.strip()
                  if (sqlNoMode != "") :
                      if (sqlNoMode[-1] ==","):
                          sqlNoMode = sqlNoMode[:-1]

              NoModeFields =feature.getAttribute('NoModeFields')
              if (NoModeFields!=""):
                  NoModeFields = "\n".join([ll.rstrip() for ll in NoModeFields.splitlines() if ll.strip()])
                  NoModeFields = NoModeFields.strip()
                  if (NoModeFields!=""):
                      if (NoModeFields[-1] ==","):
                          NoModeFields = NoModeFields[:-1]


              feature.setAttribute('NoModeFields',NoModeFields)
              feature.setAttribute('SQL_NoMode',sqlNoMode)


              self.pyoutput(feature)
          def close(self):
              pass
    PYTHONSYMBOL = FeatureProcessor
    -> AttributeCreator_5
Note: Add NumGroup
AttributeCreator_5
    ATTR_TABLE = SET_TO NumGroupTableA = FME_CONDITIONAL:DEFAULT_VALUE'-1'BOOL_OP;OR;COMPOSITE_TEST;1;TEST NumMode ATTRIBUTE_HAS_A_VALUE _FME_BLANK_STRING_'@Evaluate(@int(@Value(NumMode)/$(DimsPerGroup)))'FME_NUM_CONDITIONS2___
    -> AttributeRemover
AttributeRemover
    REMOVE_ATTRS = NumMode
    -> Output (output)
Output (output)

FME custom transformer BuildCTableJoinQueryCondition

Parameters:
- NOMODEFIELDS =
- TMODE_NAME =
- _FIELDNAME =

Input (input)
    -> Counter
Counter
    CNT_ATTR = _count
    DOMAIN = counter
    SCOPE = Local
    START = 0
    -> AttributeSplitter
    -> FeatureMerger [REQUESTOR]
AttributeSplitter
    ATTR_NAME = NoModeFields
    DELIMITER = ,
    DROP_EMPTY_PARTS = Yes
    LIST_NAME = Fields
    TRIM_OPTION = Both
    -> ListElementCounter
ListElementCounter
    CNT_ATTR = _element_count
    LIST_NAME = Fields{}
    -> TesterFieldsExist
TesterFieldsExist
    BOOL_OP = OR
    COMPOSITE_TEST = 1
    TEST_CLAUSE = TEST @Value(_element_count) > 0
    TEST_MODE = TEST
    PASSED -> ListExploder_2
    FAILED -> AttributeCreator
Note: Build a list with the condition fields
ListExploder_2
    ATTR_ACCUM_MODE = Merge List Attributes
    ATTR_CONFLICT_RES = Use List Attribute Values
    INDEX_ATTR = _element_index
    LIST_ATTR = Fields{}
    ELEMENTS -> AttributeSplitter_2
Note: Split table name and field
AttributeSplitter_2
    ATTR_NAME = Fields
    DELIMITER = .
    DROP_EMPTY_PARTS = No
    LIST_NAME = SplitField
    TRIM_OPTION = Both
    -> EqualEachField
EqualEachField: AttributeCreator
    ATTR_TABLE:
      SET_TO join_cond = CASE WHEN isnull(@Value(Fields)) then '#*#' else CAST(@Value(Fields) as string) END  =
            CASE WHEN isnull(`@Value(TMODE_Name)_C_@Value(_FieldName)`.@Value(SplitField{2})) then '#*#' else cast(`@Value(TMODE_Name)_C_@Value(_FieldName)`.@Value(SplitField{2}) as string) END
    -> JoinWithAND
Note: Empty joincondition as there are no non-agg fields
AttributeCreator
    ATTR_TABLE = SET_TO join_cond
    -> JoinWithAND
JoinWithAND: Aggregator
    ACCUM_ATTRS_NAME = Use Attributes From One Feature
    AGGREGATE_TYPE = Homogeneous Collection (If Possible)
    CONCAT_ATTRS = join_cond
    GROUP_BY = _count
    MODE = Geometry - Assemble One Level
    SEP = " AND \n "
    AGGREGATE -> AttributeRemover
AttributeRemover
    LIST_ATTRS = SplitField{}
    REMOVE_ATTRS = SplitField{0},_element_index,Fields,_element_count
    -> FeatureMerger [SUPPLIER]
FeatureMerger
    ATTR_ACCUM_MODE = Merge Supplier
    ATTR_CONFLICT_RES = Use Requestor
    IGNORE_NULLS = No
    JOIN_KEYS = @Value(_FieldName) @Value(_FieldName) AUTO
    MERGE_TYPE = Attributes Only
    PROCESS_DUPS = NO
    REJECT_NULL_MISSING_KEYS = No
    SUPPLIERS_FIRST = No
    MERGED -> Output (output)
Output (output)

FME custom transformer AddFunctionGridNumToTarget

Parameters:
- DIMGRIDSPACING =
- DIMGRIDTYPENAME =
- GRIDTYPENAME =
- TABLENAME =

Input (input)
    -> AttributeCreator_4
Note: Calculate GridTypeTarget
AttributeCreator_4
    ATTR_TABLE:
      SET_TO GridTypeTarget = FME_CONDITIONAL:DEFAULT_VALUE'10'BOOL_OP;OR;COMPOSITE_TEST;<Unused>;TEST @Value(GridTypeName) = 1km'1000'BOOL_OP;OR;COMPOSITE_TEST;<Unused>;TEST @Value(GridTypeName) = 10km'10000'BOOL_OP;OR;COMPOSITE_TEST;1;TEST @Value(GridTypeName) = 100m'100'FME_NUM_CONDITIONS4___
      SET_TO _TableName = $(TABLENAME)
    -> ExpressionEvaluator
Note: Total hectars
ExpressionEvaluator
    ACTION = Create New Attribute
    EXPRESSION = @pow(@Value(GridTypeTarget)/100,2)
    VAL_ATTR = _HectarPerCell
    -> StatisticsCalculator
Note: Find the higest scale / DimGridSpacing_max
StatisticsCalculator
    COMPUTE_HISTOGRAM = NO
    MAX_ATTR = DimGridSpacing_max
    PREPEND_ATTR_NAME_CHOICE = For multiple results only
    STATS_ATTRS = DimGridSpacing
    COMPLETE -> AttributeCreator_2
Note: Create "AddGridNumScale" function / that transforms the GridNum from / DimGridSpacing_max<GridTypeTarget && GridTypeTarget = 10000 -> Convert to 10K / DimGridSpacing_max<GridTypeTarget && GridTypeTarget = 1000 -> Convert to 1K / DimGridSpacing_max= GridTypeTarget = 10000 -> Do nothing
AttributeCreator_2
    ATTR_TABLE = SET_TO AddGridNumScale = FME_CONDITIONAL:DEFAULT_VALUE'jedi_cubes.`@Value(_TableName)`.GridNum'BOOL_OP;AND;COMPOSITE_TEST;1 AND 2;TEST @Value(DimGridSpacing_max) < @Value(GridTypeTarget);TEST @Value(GridTypeTarget) = 100'    (jedi_cubes.`@Value(_TableName)`.GridNum & cast(-65536 as bigint))'BOOL_OP;AND;COMPOSITE_TEST;<Unused>;TEST @Value(DimGridSpacing_max) < @Value(GridTypeTarget);TEST @Value(GridTypeTarget) = 1000'    (jedi_cubes.`@Value(_TableName)`.GridNum & cast(-16777216 as bigint))'BOOL_OP;AND;COMPOSITE_TEST;<Unused>;TEST @Value(DimGridSpacing_max) < @Value(GridTypeTarget);TEST @Value(GridTypeTarget) = 10000'    (jedi_cubes.`@Value(_TableName)`.GridNum & cast(-4294967296 as bigint)) 'BOOL_OP;AND;COMPOSITE_TEST;<Unused>;TEST @Value(DimGridSpacing_max) = @Value(GridTypeTarget)'jedi_cubes.`@Value(_TableName)`.`GridNum`'FME_NUM_CONDITIONS5___
    -> Output (output)
Output (output)
Add_GridTypeName_2: AttributeCreator
    ATTR_TABLE = SET_TO DimGridTypeName = @Value(_GROUP_BY)

FME custom transformer WaitUntilDatabtricksJobCompleted

Parameters:
- MINUTESTOTIMEOUT =
- RUNID =
- STARTTIME =

CheckJobStatus_Input (input)
    -> CheckRunStatus [DatabrickAPICallerInput]
CheckRunStatus: DatabricksAPICaller
    COMMAND = runs/get-output
    DOMAIN = northeurope.azuredatabricks.net
    METHOD = GET
    RUNID = @Value(RunId)
    TOKEN =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
    CallDatabricksJob_Output -> CurrentTimer
CurrentTimer: AttributeCreator
    ATTR_TABLE = SET_TO CurrentTime = @DateTimeNow()
    -> TestJobStatus
TestJobStatus: TestFilter
    DEFAULT_VALUE = <UNFILTERED>
    TEST_LIST = "BOOL_OP,OR,COMPOSITE_TEST,""""""1"""""",TEST_CLAUSE,TEST @Value(status) = TERMINATED",TERMINATED,"BOOL_OP,OR,COMPOSITE_TEST,""""""1"""""",TEST_CLAUSE,TEST @Value(status) = PENDING",PENDING,"BOOL_OP,OR,COMPOSITE_TEST,""""""1"""""",TEST_CLAUSE,TEST @Value(status) = RUNNING",RUNNING,"BOOL_OP,OR,COMPOSITE_TEST,""""""1"""""",TEST_CLAUSE,TEST @Value(status) = TERMINATING",TERMINATING
    TERMINATED -> TestFilter_TERMINATED (output)
    PENDING -> TimeOutStartingCluster
    RUNNING -> Decelerator
    TERMINATING -> Decelerator
    <UNFILTERED> -> Decelerator
TimeOutStartingCluster: Tester
    BOOL_OP = OR
    COMPOSITE_TEST = 1
    TEST_CLAUSE = TEST @Value(CurrentTime) >= @DateTimeAdd(@Value(StartTime), @DateTimeIntervalCreate(0,0,0,0,@Value(MinutesToTimeout),0) )
    TEST_MODE = TEST
    PASSED -> CancelRun [DatabrickAPICallerInput]
    FAILED -> Decelerator
CancelRun: DatabricksAPICaller
    COMMAND = runs/cancel
    DOMAIN = northeurope.azuredatabricks.net
    METHOD = POST
    RUNID = @Value(RunId)
    TOKEN =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
    CallDatabricksJob_Output -> SetErrorInDatabricksResult
SetErrorInDatabricksResult: AttributeCreator
    ATTR_TABLE:
      SET_TO error = Timeout starting cluster
      SET_TO noError = 0
      SET_TO num_records = 0
      SET_TO has_overlaps = 0
      SET_TO cmd = 0
    -> TestFilter_TERMINATED (output)
TestFilter_TERMINATED (output)
Decelerator
    DECEL_TYPE = Per Feature Delay
    DELAY = 15
    -> CheckJobStatus_Input (output)
CheckJobStatus_Input (output)

FME custom transformer G_HighToLow

Parameters:
- DIMGRIDTYPENAME =
- GRIDTYPENAME =
- G_TABLENAME =

Input (input)
    -> Aggregator
    -> FeatureMerger [REQUESTOR]
Note: Aggegrate by GridType / (10m,100m,1km,10km)
Aggregator
    ACCUM_ATTRS_NAME = Use Attributes From One Feature
    AGGREGATE_TYPE = Homogeneous Collection (If Possible)
    GROUP_BY = DimGridTypeName
    MODE = Geometry - Assemble One Level
    ORDERED = No
    SEP = ,
    AGGREGATE -> AttributeCreator_4
Note: Calculate GridTypeTargetGroup / 10,100,1000,10000
AttributeCreator_4
    ATTR_TABLE = SET_TO GridTypeTargetGroup = FME_CONDITIONAL:DEFAULT_VALUE'1'BOOL_OP;OR;COMPOSITE_TEST;1;TEST @Value(DimGridTypeName) = 10m'10'BOOL_OP;OR;COMPOSITE_TEST;<Unused>;TEST @Value(DimGridTypeName) = 100m'100'BOOL_OP;OR;COMPOSITE_TEST;<Unused>;TEST @Value(DimGridTypeName) = 1km'1000'BOOL_OP;OR;COMPOSITE_TEST;<Unused>;TEST @Value(DimGridTypeName) = 10km'10000'FME_NUM_CONDITIONS5___
    -> Sorter
Note: Sort the scales
Sorter
    SORT_PARM = GridTypeTargetGroup NUMERIC ASCENDING
    SORTED -> Counter
Counter
    CNT_ATTR = NumScales
    DOMAIN = counter
    SCOPE = Local
    START = 0
    -> AttributeCreator
Note: Get the next scale
AttributeCreator
    ATTR_TABLE:
      SET_TO GridTypeTargetGroupNext = @Value(feature[+1].GridTypeTargetGroup)
      SET_TO GridTypeTarget = FME_CONDITIONAL:DEFAULT_VALUE'_FME_NO_OP_'BOOL_OP;OR;COMPOSITE_TEST;1;TEST @Value(DimGridTypeName) = 1m'1'BOOL_OP;OR;COMPOSITE_TEST;1;TEST @Value(DimGridTypeName) = 10m'10'BOOL_OP;OR;COMPOSITE_TEST;1;TEST @Value(DimGridTypeName) = 100m'100'BOOL_OP;OR;COMPOSITE_TEST;1;TEST @Value(DimGridTypeName) = 1km'1000'BOOL_OP;OR;COMPOSITE_TEST;1;TEST @Value(DimGridTypeName) = 10km'10000'FME_NUM_CONDITIONS6___
    NUM_PRIOR_FEATURES = 0
    NUM_SUBSEQUENT_FEATURES = 1
    -> AttributeCreator_2
Note: Get the next scale
AttributeCreator_2
    ATTR_TABLE:
      SET_TO GridTypeTargetGroupNext = FME_CONDITIONAL:DEFAULT_VALUE'_FME_NO_OP_'BOOL_OP;OR;COMPOSITE_TEST;1;TEST @Value(GridTypeTargetGroupNext) = 10'10m'BOOL_OP;OR;COMPOSITE_TEST;1;TEST @Value(GridTypeTargetGroupNext) = 100'100m'BOOL_OP;OR;COMPOSITE_TEST;1;TEST @Value(GridTypeTargetGroupNext) = 1000'1km'BOOL_OP;OR;COMPOSITE_TEST;1;TEST @Value(GridTypeTargetGroupNext) = 10000'10km'FME_NUM_CONDITIONS5___
      SET_TO GridTypeTarget = FME_CONDITIONAL:DEFAULT_VALUE'_FME_NO_OP_'BOOL_OP;OR;COMPOSITE_TEST;1;TEST @Value(GridTypeTarget) = 10'10m'BOOL_OP;OR;COMPOSITE_TEST;1;TEST @Value(GridTypeTarget) = 100'100m'BOOL_OP;OR;COMPOSITE_TEST;1;TEST @Value(GridTypeTarget) = 1000'1km'BOOL_OP;OR;COMPOSITE_TEST;1;TEST @Value(GridTypeTarget) = 10000'10km'FME_NUM_CONDITIONS5___
    NUM_PRIOR_FEATURES = 0
    NUM_SUBSEQUENT_FEATURES = 1
    -> G_HighToLowTableName
G_HighToLowTableName: AttributeCreator
    ATTR_TABLE = SET_TO G_HighToLowName = @Value(G_TableName)_HighToLow_@Value(GridTypeTargetGroupNext)
    -> PythonCaller
PythonCaller
    NEW_ATTRIBUTES = G_HighToLowQuery
    PYTHONSOURCE:
      import fme
      import fmeobjects
      # Template Function interface:
      # When using this function, make sure its name is set as the value of
      # the 'Class or Function to Process Features' transformer parameter
      def processFeature(feature):
          pass

      # Template Class Interface:
      # When using this class, make sure its name is set as the value of
      # the 'Class or Function to Process Features' transformer parameter
      class FeatureProcessor(object):
          def __init__(self):
              pass
          def input(self,feature):
              if (feature.getAttribute('G_HighToLowName')==feature.getAttribute('G_TableName')+"_HighToLow_"):
                  SQL =""
              else:
                  numScales= str(feature.getAttribute('NumScales'))
                  tableName1 = "jedi_cubes." +  feature.getAttribute('G_TableName').replace("G_","F_") + "_" + feature.getAttribute('DimGridTypeName')
                  if (numScales != "0"):
                      tableName1 = "jedi_cubes."+feature.getAttribute('G_TableName')+"_HighToLow_" +  feature.getAttribute('GridTypeTarget')

                  tableName2 = "jedi_cubes." +  feature.getAttribute('G_TableName').replace("G_","F_") + "_" + feature.getAttribute('GridTypeTargetGroupNext')


                  fields1= ""
                  fields2= ""
                  feature.getAttribute('GridTypeTargetGroupNext')
                  to10m = "-256"
                  to100m ="-65536"
                  to1km ="-16777216"
                  to10km = "-4294967296"


                  SQL ="SELECT GridNum10km  "
                  if (feature.getAttribute('GridTypeTargetGroupNext') == "10m"):
                     fields2 = ",(GridNum & cast(" + to10m + " as bigint)) as GridNum" + feature.getAttribute('GridTypeTargetGroupNext')
                     #if (feature.getAttribute('GridTypeTargetGroupNext') != feature.getAttribute('GridTypeName')):
                     fields2 = fields2 + ",(GridNum & cast(" + to100m + " as bigint)) as GridNum100m,(GridNum & cast(" + to1km + " as bigint)) as GridNum1km "

                     if (numScales != "0"):
                         fields1 = ",GridNum"+  feature.getAttribute('GridTypeTargetGroupNext')
                         #if (feature.getAttribute('GridTypeTargetGroupNext') != feature.getAttribute('GridTypeName')):
                         fields1 = fields1 + ",GridNum100m,GridNum1km"
                     else:
                         fields1= fields2


                  elif (feature.getAttribute('GridTypeTargetGroupNext') == "100m"):
                     fields2 =  ",(GridNum & cast(" + to100m  + " as bigint)) as GridNum" + feature.getAttribute('GridTypeTargetGroupNext')
                     #if (feature.getAttribute('GridTypeTargetGroupNext') != feature.getAttribute('GridTypeName')):
                     fields2 = fields2 + ",(GridNum & cast(" + to1km + " as bigint)) as GridNum1km "

                     if (numScales != "0"):
                         fields1 = ",GridNum"+  feature.getAttribute('GridTypeTargetGroupNext')
                         #if (feature.getAttribute('GridTypeTargetGroupNext') != feature.getAttribute('GridTypeName')):
                         fields1 = fields1 + ",GridNum1km"
                     else:
                         fields1= fields2

                  elif (feature.getAttribute('GridTypeTargetGroupNext') == "1km"):
                     fields2 =  ",(GridNum & cast(" + to1km  + " as bigint)) as GridNum" + feature.getAttribute('GridTypeTargetGroupNext')
                     fields1 = ",GridNum" + feature.getAttribute('GridTypeTargetGroupNext')



                  SQL = SQL + fields1   + " FROM " + tableName1


                  SQL = SQL  + " UNION " + " SELECT GridNum10km "  + fields2
                  SQL = SQL + " FROM " + tableName2

              feature.setAttribute("G_HighToLowQuery",SQL)
              self.pyoutput(feature)

          def close(self):
              pass
    PYTHONSYMBOL = FeatureProcessor
    -> AttributeKeeper
AttributeKeeper
    CREATE_BULK_MODE_FEATURES = NO
    KEEP_ATTRS = G_HighToLowName,G_HighToLowQuery,DimGridTypeName,GridTypeName,NumScales
    -> FeatureMerger [SUPPLIER]
Note: Remap new value to all values
FeatureMerger
    ATTR_ACCUM_MODE = Merge Supplier
    ATTR_CONFLICT_RES = Use Requestor
    GROUP_BY = DimGridTypeName
    IGNORE_NULLS = No
    JOIN_KEYS = 1 1 AUTO
    MERGE_TYPE = Attributes Only
    PROCESS_DUPS = NO
    REJECT_NULL_MISSING_KEYS = No
    SUPPLIERS_FIRST = No
    MERGED -> Output (output)
Output (output)

FME custom transformer DeleteCubeStats

Parameters:
- CUBEID =
- fields =

Initiator (input)
    -> Counter
    -> DatabaseDeleter
DatabaseDeleter
    CONDITION = WHERE Clause
    DATASET = CubeManager
    FORMAT = MSSQL_JDBC_NONSPATIAL
    MSSQL_JDBC_NONSPATIAL_NAMED_CONNECTION = CubeManager
    MSSQL_JDBC_NONSPATIAL_QUERY_FEATURE_TYPES_FOR_MERGE_FILTERS = Yes
    MSSQL_JDBC_NONSPATIAL_QUERY_TIMEOUT = 30
    TABLE = dbo.CubeFieldStatistics
    WHERE_CLAUSE:
      CubeFieldId
      IN (
      select CubeFieldId
      from
      	CubeFields
      where cubeid  = @Value(CubeId)
      )
Iterator (input)
    -> Counter
Counter
    CNT_ATTR = _count
    DOMAIN = counter
    SCOPE = Global
    START = 1
    -> SQLExecutor [INITIATOR]
SQLExecutor
    COMBINE_ATTRS = Result Attributes Only
    COMBINE_GEOM = Initiator Geometry Only
    DATASET = CubeManager
    EXPOSED_ATTRIBUTE_LIST = CubeId NumFields
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = CubeManager
    MSSQL_ADO_QUERY_FEATURE_TYPES_FOR_MERGE_FILTERS = Yes
    SQL_STATEMENT:
      select cubeid,count(CubeFieldStatistics.CubeFieldId) as NumFields
      from cubefields inner join
      	CubeFieldStatistics  on CubeFields.CubeFieldId = CubeFieldStatistics.CubeFieldId
      where cubeid = $(CUBEID)
      Group BY
      	cubeid
    RESULT -> ParameterFetcher_2
    INITIATOR -> Tester
ParameterFetcher_2
    ATTR_LIST = fields $(fields)
    -> TestFilter
TestFilter
    DEFAULT_VALUE = NoFields
    TEST_LIST = "BOOL_OP,OR,COMPOSITE_TEST,""""""1"""""",TEST_CLAUSE,TEST @Value(NumFields) > 0",Fields
    Fields -> Decelerator
    NoFields -> Output (output)
Decelerator
    DECEL_TYPE = Per Feature Delay
    DELAY = 15
    -> Iterator (output)
Iterator (output)
Tester
    BOOL_OP = AND
    COMPOSITE_TEST = 1 AND 2
    TEST_CLAUSE:
      TEST @Value(_count) = 1
      TEST @Value(_matched_records) = 0
    TEST_MODE = TEST
    PASSED -> Output (output)
Output (output)

FME custom transformer ProduceSQLJOINString

Parameters:
- _DATABASEOWNER =
- _JOIN_FIELD_NAME =
- _JOIN_TABLE_NAME =
- _JOIN_TYPE =
- _SOURCE_FIELD_NAME =
- _SOURCE_TABLE_NAME =
- _TOTALINDENTS =

Input (input)
    -> AttributeCreator_3
AttributeCreator_3
    ATTR_TABLE = SET_TO _tempSpacing
    -> StringPadder
Note: Add indents to make the / TSQL look nice
StringPadder
    BLANK_ATTRIBUTE = Yes
    PADCHAR = "\t"
    SIDE = Left
    SRC_ATTRS = _tempSpacing
    WIDTH = @Value(_TotalIndents)
    -> Counter
Counter
    CNT_ATTR = _CounterSQLJOINString
    DOMAIN = _CounterSQLJOINString
    SCOPE = Local
    START = 0
    -> AttributeSplitter
NextField (input)
    -> ExpressionEvaluator
ExpressionEvaluator
    ACTION = Overwrite Existing Attributes
    ATTRLIST = _fieldscounter
    EXPRESSION = @Value(_fieldscounter)-1
    -> AttributeCreator
Note: TSQL Add / <Table>.<Field> = <Table.Field>
AttributeCreator
    ATTR_TABLE = SET_TO __SQLJoin = FME_CONDITIONAL:DEFAULT_VALUE''BOOL_OP;AND;COMPOSITE_TEST;<Unused>;TEST @Value(_Source_Table_Name) ATTRIBUTE_HAS_VALUE _FME_BLANK_STRING_;TEST @Value(_Join_Table_Name) ATTRIBUTE_HAS_VALUE _FME_BLANK_STRING_;TEST @Value(_Join_Field_Name) ATTRIBUTE_HAS_VALUE _FME_BLANK_STRING_;TEST @Value(_Source_Field_Name) ATTRIBUTE_HAS_VALUE _FME_BLANK_STRING_'@Value(_tempSpacing)@Value(_DatabaseOwner).`@Value(_Join_Table_Name)`.`@Value(_Join_Field_Name{@Value(_fieldscounter)})` = jedi_cubes.`@Value(_Source_Table_Name)`.`@Value(_Source_Field_Name{@Value(_fieldscounter)})`'BOOL_OP;AND;COMPOSITE_TEST;<Unused>;TEST @Value(_Source_Table_Name) NOT_ATTRIBUTE_HAS_VALUE _FME_BLANK_STRING_;TEST @Value(_Join_Table_Name) ATTRIBUTE_HAS_VALUE _FME_BLANK_STRING_;TEST @Value(_Join_Field_Name) ATTRIBUTE_HAS_VALUE _FME_BLANK_STRING_;TEST @Value(_Source_Field_Name) ATTRIBUTE_HAS_VALUE _FME_BLANK_STRING_'@Value(_tempSpacing)@Value(_DatabaseOwner).`@Value(_Join_Table_Name)`.`@Value(_Join_Field_Name{@Value(_fieldscounter)})` = `@Value(_Source_Field_Name{@Value(_fieldscounter)})`'FME_NUM_CONDITIONS3___
    -> TestFilter
TestFilter
    DEFAULT_VALUE = Continue
    TEST_LIST = BOOL_OP,OR,COMPOSITE_TEST,<Unused>,TEST_CLAUSE,"TEST @Value(_fieldscounter) = 0",Finished
    Finished -> Aggregator
    Continue -> NextField (output)
    Continue -> Aggregator
Aggregator
    ACCUM_ATTRS_NAME = Use Attributes From One Feature
    AGGREGATE_TYPE = Homogeneous Collection (If Possible)
    CONCAT_ATTRS = __SQLJoin
    GROUP_BY = _CounterSQLJOINString
    MODE = Geometry - Assemble One Level
    ORDERED = Yes
    SEP = "\n\t\tAND \n        "
    AGGREGATE -> AttributeCreator_2
Note: TSQL ADD / LEFT JOIN <TABLE> ON ...
AttributeCreator_2
    ATTR_TABLE:
      SET_TO __SQLJoin = FME_CONDITIONAL:DEFAULT_VALUE''BOOL_OP;AND;COMPOSITE_TEST;<Unused>;TEST @Value(_Source_Table_Name) ATTRIBUTE_HAS_VALUE _FME_BLANK_STRING_;TEST @Value(_Join_Table_Name) ATTRIBUTE_HAS_VALUE _FME_BLANK_STRING_;TEST @Value(_Join_Field_Name) ATTRIBUTE_HAS_VALUE _FME_BLANK_STRING_;TEST @Value(_Source_Field_Name) ATTRIBUTE_HAS_VALUE _FME_BLANK_STRING_'@Value(_Join_Type) JOIN @Value(_DatabaseOwner).`@Value(_Join_Table_Name)`
        	ON @Value(__SQLJoin)'BOOL_OP;AND;COMPOSITE_TEST;<Unused>;TEST @Value(_Source_Table_Name) NOT_ATTRIBUTE_HAS_VALUE _FME_BLANK_STRING_;TEST @Value(_Join_Table_Name) ATTRIBUTE_HAS_VALUE _FME_BLANK_STRING_;TEST @Value(_Join_Field_Name) ATTRIBUTE_HAS_VALUE _FME_BLANK_STRING_;TEST @Value(_Source_Field_Name) ATTRIBUTE_HAS_VALUE _FME_BLANK_STRING_'@Value(_Join_Type) JOIN jedi_cubes.`@Value(_Join_Table_Name)`
        	ON @Value(__SQLJoin)'FME_NUM_CONDITIONS3___
    -> Output (output)
Output (output)
NextField (output)

Bookmark: PUT Fields into a LIST
AttributeSplitter
    ATTR_NAME = _Join_Field_Name
    DELIMITER = ,
    DROP_EMPTY_PARTS = No
    LIST_NAME = _Join_Field_Name
    TRIM_OPTION = Both
    -> AttributeSplitter_2
AttributeSplitter_2
    ATTR_NAME = _Source_Field_Name
    DELIMITER = ,
    DROP_EMPTY_PARTS = No
    LIST_NAME = _Source_Field_Name
    TRIM_OPTION = Both
    -> ListElementCounter
Note: How many fields do we have
ListElementCounter
    CNT_ATTR = _fieldscounter
    LIST_NAME = _Join_Field_Name{}
    -> ExpressionEvaluator
