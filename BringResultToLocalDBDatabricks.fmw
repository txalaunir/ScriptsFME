FME workspace BringResultToLocalDBDatabricks.fmw
Title: Move data back to local data warehouse
Description: Exports tables form SQL Datawarehouse into Azure blob, re-import these tables back into a local SQL Server 2016 database.
Usage: PARAMETERS:
    CubeId: The CubeId-number that needs to be transfered. Only a specific set of tables will be moved to the local infrastructure. 
    NOTE FOR THE DEVELOPERS:
If we encounter errors during the creation of the tables check the data types and definitions as they are not the same from blob to database.
History: 15/02/2017,Jan Bliki,Creation of process

Parameters:
- CubeId = 220
- WriteTablesOnSqlServer = 0

Note: Find CUBE details
SQLCreator
    DATASET = CubeManager
    EXPOSED_ATTRIBUTE_LIST = CreationDate,CubeId,DeleteFlag,GridTypeId,Name,ProcessCube,Title
    FORMAT = MSSQL_ADO
    MSSQL_ADO_COMMAND_TIMEOUT = 0
    MSSQL_ADO_NAMED_CONNECTION = CubeManager
    MSSQL_ADO_QUERY_FEATURE_TYPES_FOR_MERGE_FILTERS = Yes
    SQL_STATEMENT:
      /****** Script for SelectTopNRows command from SSMS  ******/
      SELECT [CubeId]
            ,[GridTypeId]
            ,[Name]
            ,[Title]
            ,[CreationDate]
            ,[ProcessCube]
            ,[DeleteFlag]
        FROM [CubeManager].[dbo].[Cubes]
        WHERE CubeId=$(CubeId)
        and DeleteFlag=0
    RESULT -> AttributeCreator_13
Note: Database name
AttributeCreator_13
    ATTR_TABLE = SET_TO DatabaseName = JEDI_@Value(Name)
    -> AttributeCreator_20
Note: Create database if not existing
CreateDatabase
    DATABASENAME = @Value(DatabaseName)
    -> AttributeCreator_22
    -> DateFormatter
AttributeCreator_22
    ATTR_TABLE:
      SET_TO TransformerPath = CreateDataBase
      SET_TO MessageString = Create database if not existing
    -> AttributeCreator_20_OUTPUT_-__AttributeCreator_INFO_2
DateFormatter
    DATE_ATTR = CreationDate
    FMT = %d_%m_%Y
    INVALID_DATE_VALUE = _FME_NO_OP_
    SRCFMT = Unknown - Automatic Detection
    -> AttributeCreator_30
Note: Create table names attributes
AttributeCreator_30
    ATTR_TABLE:
      SET_TO TableName = C_@Value(Name)
      SET_TO CTableName = C_@Value(Name)
      SET_TO FTableName = F_@Value(Name)
    -> TestFilter
Note: Table name should not / contain [ or ] as we going / to use that name in other cases.
TestFilter
    DEFAULT_VALUE = FailedTableName
    TEST_LIST:
      BOOL_OP,AND,COMPOSITE_TEST,<Unused>,TEST_CLAUSE,"TEST @Value(TableName) ATTRIBUTE_HAS_VALUE """"
      TEST @Value(TableName) NOT_CONTAINS [
      TEST @Value(TableName) NOT_CONTAINS ]",TableNameOk
    TableNameOk -> CreateCubeTable_CTable
    FailedTableName -> AttributeCreator_10
CreateCubeTable_CTable
    CubeId = @Value(CubeId)
    DatabaseName = @Value(DatabaseName)
    TableName = @Value(CTableName)
    Info_1 -> AttributeCreator_20_OUTPUT_-__AttributeCreator_INFO_2
    Info_2 -> AttributeCreator_27_OUTPUT_-__AttributeCreator_INFO_2
    SQLExecutor_12_Initiator -> WriteTablesOnSqlServer
    Error -> AttributeCreator_6_OUTPUT_-__SQLExecutor_6_INITIATOR
WriteTablesOnSqlServer: TestFilter
    DEFAULT_VALUE = NotWriteOnDB
    TEST_LIST = "BOOL_OP,OR,COMPOSITE_TEST,""""""1"""""",TEST_CLAUSE,TEST $(WriteTablesOnSqlServer) = 1",WriteOnDB
    WriteOnDB -> CreateCubeTable_FTable
    NotWriteOnDB -> SQLExecutor_7 [INITIATOR]
CreateCubeTable_FTable
    CubeId = @Value(CubeId)
    DatabaseName = @Value(DatabaseName)
    TableName = @Value(FTableName)
    Info_1 -> AttributeCreator_20_OUTPUT_-__AttributeCreator_INFO_2
    Info_2 -> AttributeCreator_27_OUTPUT_-__AttributeCreator_INFO_2
    SQLExecutor_12_Initiator -> SQLExecutor_7 [INITIATOR]
    Error -> AttributeCreator_6_OUTPUT_-__SQLExecutor_6_INITIATOR
Note: INFO
AttributeCreator_20_OUTPUT_-__AttributeCreator_INFO_2: Junction
    -> AttributeCreator_INFO_2
Note: INFO
AttributeCreator_27_OUTPUT_-__AttributeCreator_INFO_2: Junction
    -> AttributeCreator_INFO_2
AttributeCreator_29
    ATTR_TABLE:
      SET_TO TransformerPath = MOVELOOKTABLES\SQLExecutor_7
      SET_TO MessageString = Move look tables initiator
    -> AttributeCreator_15_OUTPUT_-__AttributeCreator_INFO_2
AttributeCreator_14
    ATTR_TABLE:
      SET_TO MessageString = Failed to copy lookup table dbo.[@Value(LookupTable)]
      SET_TO TransformerPath = SQLExecutor_8
    -> AttributeCreator_6_OUTPUT_-__SQLExecutor_6_INITIATOR
Note: Set flags in CubeManager-Database
SQLExecutor_5
    COMBINE_ATTRS = Result Attributes Only
    COMBINE_GEOM = Initiator Geometry Only
    DATASET = CubeManager
    FORMAT = MSSQL_ADO
    MSSQL_ADO_APPLICATION_INTENT = ReadWrite
    MSSQL_ADO_COMMAND_TIMEOUT = 0
    MSSQL_ADO_CREATE_FEATURE_TABLES_FROM_DATA = Yes
    MSSQL_ADO_NAMED_CONNECTION = CubeManager
    MSSQL_ADO_QUERY_FEATURE_TYPES_FOR_MERGE_FILTERS = Yes
    SQL_STATEMENT:
      UPDATE dbo.CUBES
          set [FMEJobIdMoveToLocalDBDate] = getdate(),
              [FMEJobIdMovetoLocalDBStatus] = 1,
              [ErrorMessages]=null,
              StatusPercentage= 66
      WHERE CubeId = $(CubeId)
    INITIATOR -> DeleteBlobContent_2_Deleted
    INITIATOR -> AttributeCreator_15
    <REJECTED> -> AttributeCreator_9
AttributeCreator_15
    ATTR_TABLE:
      SET_TO MessageString = Field FMEJobIdMovetoLocalDBStatus Updated
      SET_TO TransformerPath = SQLExecutor_8
    -> AttributeCreator_15_OUTPUT_-__AttributeCreator_INFO_2
Note: INFO
AttributeCreator_15_OUTPUT_-__AttributeCreator_INFO_2: Junction
    -> AttributeCreator_INFO_2
AttributeCreator_INFO_2: Junction
    -> AttributeCreator_INFO
AttributeCreator_INFO
    ATTR_TABLE = SET_TO MessageType = INFO
    -> AttributeKeeper
DeleteBlobContent_2_Deleted: Logger [off]
    MAXCOORDS = 20
    MAXFEATS = 20
    MESSAGE = Feature is:
AttributeCreator_9
    ATTR_TABLE:
      SET_TO MessageString = Failed to set flags in CubeManager
      SET_TO TransformerPath = SQLExecutor_5
    -> SQLExecutor_6_INITIATOR
AttributeCreator_10
    ATTR_TABLE:
      SET_TO MessageString = TableName contains "[" or "]" or is empty. (@Value(TableName))
      SET_TO TransformerPath = TestFilter
    -> AttributeCreator_6_OUTPUT_-__SQLExecutor_6_INITIATOR
AttributeCreator_6_OUTPUT_-__SQLExecutor_6_INITIATOR: Junction
    -> SQLExecutor_6_INITIATOR
SQLExecutor_6_INITIATOR: Junction
    -> SQLExecutor_6 [INITIATOR]
Note: Set flags in CubeManager-Database / And report Error to database
SQLExecutor_6
    COMBINE_ATTRS = Result Attributes Only
    COMBINE_GEOM = Initiator Geometry Only
    DATASET = CubeManager
    FORMAT = MSSQL_ADO
    MSSQL_ADO_APPLICATION_INTENT = ReadWrite
    MSSQL_ADO_COMMAND_TIMEOUT = 0
    MSSQL_ADO_CREATE_FEATURE_TABLES_FROM_DATA = Yes
    MSSQL_ADO_NAMED_CONNECTION = CubeManager
    MSSQL_ADO_QUERY_FEATURE_TYPES_FOR_MERGE_FILTERS = Yes
    SQL_STATEMENT:
      UPDATE dbo.CUBES
          set [FMEJobIdMoveToLocalDBDate] = getdate(),
              [FMEJobIdMovetoLocalDBStatus] = 0,
              [ErrorMessages]=N'@Value(MessageString)'
      WHERE CubeId = $(CubeId)
    INITIATOR -> AttributeCreator_ERROR
    <REJECTED> -> AttributeCreator
AttributeCreator
    ATTR_TABLE:
      SET_TO MessageString = Error: @Value(_reader_error).
        WorkSpace: $(WORKSPACE_NAME)
        Transformer name:  SQLDosExecutor_6

      SET_TO TransformerPath = SQLExecutor_6
    -> AttributeCreator_ERROR
AttributeCreator_ERROR
    ATTR_TABLE = SET_TO MessageType = ERROR
    -> AttributeKeeper
AttributeKeeper
    CREATE_BULK_MODE_FEATURES = No
    KEEP_ATTRS = CubeId,MessageType,MessageString,TransformerPath
    -> JediLogWritter
JediLogWritter
    FILEID = @Value(CubeId)
    MESSAGESTRING = @Value(MessageString)
    MESSAGETYPE = @Value(MessageType)
    OBJECTPROCESSED = Cube
    SQLServerConn = CubeManager
    TRANSFORMERPATH = $(WORKSPACE_NAME)\StepB: MOVE TO LOCAL DB\@Value(TransformerPath)
    -> Tester
Tester
    BOOL_OP = OR
    TEST_CLAUSE = TEST @Value(MessageType) = ERROR
    TEST_MODE = TEST
    PASSED -> Terminator_3
Terminator_3 [off]
    MESSAGE = Failed execution: @Value(MessageString)

Bookmark: Tell DB we are executing the job
Note: Reset the database and provide the job_id so log information can be found easily.
AttributeCreator_20
    ATTR_TABLE = SET_TO _FME_JOB_ID = FME_CONDITIONAL:DEFAULT_VALUE'$(FME_JOB_ID)'BOOL_OP;AND;COMPOSITE_TEST;<Unused>;TEST $(FME_JOB_ID) ATTRIBUTE_IS_MISSING _FME_BLANK_STRING_;TEST $(FME_JOB_ID) NOT_ATTRIBUTE_HAS_VALUE _FME_BLANK_STRING_'-1'FME_NUM_CONDITIONS2___
    -> SQLExecutor_2 [INITIATOR]
SQLExecutor_2
    COMBINE_ATTRS = Result Attributes Only
    COMBINE_GEOM = Initiator Geometry Only
    DATASET = CubeManager
    FORMAT = MSSQL_ADO
    MSSQL_ADO_COMMAND_TIMEOUT = 30
    MSSQL_ADO_CREATE_FEATURE_TABLES_FROM_DATA = Yes
    MSSQL_ADO_NAMED_CONNECTION = CubeManager
    MSSQL_ADO_QUERY_FEATURE_TYPES_FOR_MERGE_FILTERS = Yes
    SQL_STATEMENT:
      update [dbo].[Cubes]
          set FMEJobIdMoveToLocalDB=@Value(_FME_JOB_ID),
              [FMEJobIdMoveToLocalDBDate] = NULL,
              [FMEJobIdMovetoLocalDBStatus]=0
      where CubeId = @Value(CubeId)
    INITIATOR -> CreateDatabase [Initiator]

Bookmark: MOVE LOOKUP TABLES
Note: Find all Lookup tables / and copy those to the database
SQLExecutor_7
    COMBINE_ATTRS = Keep Initiator Attributes if Conflict
    COMBINE_GEOM = Initiator Geometry Only
    DATASET = CubeManager
    EXPOSED_ATTRIBUTE_LIST = LookupTable,AzureLookupFile,Fields
    FORMAT = MSSQL_ADO
    MSSQL_ADO_APPLICATION_INTENT = ReadWrite
    MSSQL_ADO_COMMAND_TIMEOUT = 0
    MSSQL_ADO_CREATE_FEATURE_TABLES_FROM_DATA = Yes
    MSSQL_ADO_NAMED_CONNECTION = CubeManager
    MSSQL_ADO_QUERY_FEATURE_TYPES_FOR_MERGE_FILTERS = Yes
    SQL_STATEMENT:
      select distinct 'L_' + L.Name as LookupTable, L.AzureLookupFile,
      STUFF(
      		(SELECT
      			',[' + LF.FieldName + '] ' +
      			case when LF.FieldType='text' then 'nvarchar(4000)'
      			--case when LF.FieldType like 'varchar*' then 'varchar*'
      			else LF.FieldType
      			end
      		 FROM
      			 [CubeManager].dbo.LookupFields LF
               WHERE
      			LF.LookupId = L.LookupId

      					order by
      			lf.FieldOrder

      			FOR XML PATH('')


      			), 1, 1, ''
      	) Fields
      from [CubeManager].dbo.lookups L inner join
      	 [CubeManager].dbo.LookupFields LF  ON  L.LookupId = LF.LookupId inner join
      	 [CubeManager].dbo.CubeFields CF on LF.LookupFieldId = CF.LookupFieldId
      where CF.CubeId = @Value(CubeId)
    RESULT -> SQLExecutor_8 [INITIATOR]
    INITIATOR -> AttributeCreator_29
    INITIATOR -> NoLUTs
    <REJECTED> -> AttributeCreator_6
Note: Move lookup table
SQLExecutor_8
    COMBINE_ATTRS = Result Attributes Only
    COMBINE_GEOM = Initiator Geometry Only
    DATASET = LocalJedi
    FORMAT = MSSQL_ADO
    MSSQL_ADO_APPLICATION_INTENT = ReadWrite
    MSSQL_ADO_COMMAND_TIMEOUT = 0
    MSSQL_ADO_CREATE_FEATURE_TABLES_FROM_DATA = Yes
    MSSQL_ADO_NAMED_CONNECTION = LocalJedi
    MSSQL_ADO_QUERY_FEATURE_TYPES_FOR_MERGE_FILTERS = Yes
    SQL_STATEMENT:
      FME_SQL_DELIMITER ;
      USE @Value(DatabaseName);

      if exists (select top 1 name from sysobjects where name = '@Value(LookupTable)_External' and xtype = 'ET')
      	DROP EXTERNAL TABLE dbo.[@Value(LookupTable)_External];

      -- CREATE EXTERNAL TABLE based on the FME information
      CREATE EXTERNAL TABLE dbo.[@Value(LookupTable)_External] (
      	@Value(Fields)
      )
      WITH (
      	LOCATION = '@Value(AzureLookupFile)',
      	DATA_SOURCE= AzureStorage,
      	FILE_FORMAT= TextFileVerticalLineGz,
          REJECT_TYPE=value,
          REJECT_VALUE=1
      );
    INITIATOR -> SQLExecutor_3 [INITIATOR]
    <REJECTED> -> AttributeCreator_14
Note: Move lookup table
SQLExecutor_3
    COMBINE_ATTRS = Result Attributes Only
    COMBINE_GEOM = Initiator Geometry Only
    DATASET = LocalJedi
    FORMAT = MSSQL_ADO
    MSSQL_ADO_APPLICATION_INTENT = ReadWrite
    MSSQL_ADO_COMMAND_TIMEOUT = 0
    MSSQL_ADO_CREATE_FEATURE_TABLES_FROM_DATA = Yes
    MSSQL_ADO_NAMED_CONNECTION = LocalJedi
    MSSQL_ADO_QUERY_FEATURE_TYPES_FOR_MERGE_FILTERS = Yes
    SQL_STATEMENT:
      FME_SQL_DELIMITER ;

      USE @Value(DatabaseName);
      IF  EXISTS (SELECT [name] FROM sys.objects WHERE [name] = '@Value(LookupTable)')
      BEGIN
          DROP TABLE [dbo].[@Value(LookupTable)]
      END

      SELECT *
      INTO [dbo].[@Value(LookupTable)]
      FROM [dbo].[@Value(LookupTable)_External];


      DROP EXTERNAL TABLE [dbo].[@Value(LookupTable)_External]
    INITIATOR -> SQLExecutor_5 [INITIATOR]
    <REJECTED> -> AttributeCreator_14
NoLUTs: Tester
    BOOL_OP = OR
    COMPOSITE_TEST = 1
    TEST_CLAUSE = TEST @Value(_matched_records) = 0
    TEST_MODE = TEST
    PASSED -> SQLExecutor_5 [INITIATOR]
AttributeCreator_6
    ATTR_TABLE:
      SET_TO MessageString = Failed to copy lookup table dbo.[@Value(LookupTable)]
      SET_TO TransformerPath = SQLExecutor_7
    -> AttributeCreator_6_OUTPUT_-__SQLExecutor_6_INITIATOR

FME custom transformer CreateDatabase

Parameters:
- DATABASENAME = @Value(DatabaseName)   # DatabaseName

Initiator (input)
    -> SQLExecutor_2 [INITIATOR]
Note: Test if database exists
SQLExecutor_2
    COMBINE_ATTRS = Keep Initiator Attributes if Conflict
    COMBINE_GEOM = Initiator Geometry Only
    DATASET = LocalJedi
    FORMAT = MSSQL_ADO
    MSSQL_ADO_COMMAND_TIMEOUT = 0
    MSSQL_ADO_NAMED_CONNECTION = LocalJedi
    MSSQL_ADO_QUERY_FEATURE_TYPES_FOR_MERGE_FILTERS = Yes
    SQL_STATEMENT:
      select [name]
      from sys.databases where name = '@Value(DatabaseName)'
    INITIATOR -> TestFilter
TestFilter
    DEFAULT_VALUE = NotExists
    TEST_LIST = BOOL_OP,OR,COMPOSITE_TEST,<Unused>,TEST_CLAUSE,"TEST @Value(_matched_records) = 1",Exists
    Exists -> SQLExecutor_3 [INITIATOR]
    NotExists -> SQLExecutor_8 [INITIATOR]
Note: Drop the database
SQLExecutor_3
    COMBINE_ATTRS = Result Attributes Only
    COMBINE_GEOM = Initiator Geometry Only
    DATASET = LocalJedi
    FORMAT = MSSQL_ADO
    MSSQL_ADO_APPLICATION_INTENT = ReadWrite
    MSSQL_ADO_COMMAND_TIMEOUT = 0
    MSSQL_ADO_CREATE_FEATURE_TABLES_FROM_DATA = Yes
    MSSQL_ADO_NAMED_CONNECTION = LocalJedi
    MSSQL_ADO_QUERY_FEATURE_TYPES_FOR_MERGE_FILTERS = Yes
    SQL_STATEMENT:
      FME_SQL_DELIMITER ;

      DROP DATABASE [@Value(DatabaseName)]
    INITIATOR -> Decelerator
    <REJECTED> -> Output (output)
Decelerator
    DECEL_TYPE = Per Feature Delay
    DELAY = 20
    -> SQLExecutor_8 [INITIATOR]
Note: Create a new database
SQLExecutor_8
    COMBINE_ATTRS = Result Attributes Only
    COMBINE_GEOM = Initiator Geometry Only
    DATASET = LocalJedi
    FORMAT = MSSQL_ADO
    MSSQL_ADO_APPLICATION_INTENT = ReadWrite
    MSSQL_ADO_COMMAND_TIMEOUT = 0
    MSSQL_ADO_CREATE_FEATURE_TABLES_FROM_DATA = Yes
    MSSQL_ADO_NAMED_CONNECTION = LocalJedi
    MSSQL_ADO_QUERY_FEATURE_TYPES_FOR_MERGE_FILTERS = Yes
    SQL_STATEMENT:
      FME_SQL_DELIMITER ;
      USE master;
      /****** Object:  Database [@Value(DatabaseName)]    Script Date: 11/04/2018 13:57:22 ******/


      CREATE DATABASE [@Value(DatabaseName)]
       CONTAINMENT = NONE
       ON  PRIMARY
      ( NAME = N'@Value(DatabaseName)', FILENAME = N'\\cifs_svm12\teal_data01\Program Files\Microsoft SQL Server\MSSQL13.MSSQLSERVER\MSSQL\Data\@Value(DatabaseName).mdf' , SIZE = 16195584KB , MAXSIZE = UNLIMITED, FILEGROWTH = 65536KB ),
      ( NAME = N'@Value(DatabaseName)1', FILENAME = N'\\cifs_svm12\teal_data01\Program Files\Microsoft SQL Server\MSSQL13.MSSQLSERVER\MSSQL\Data\@Value(DatabaseName)1.ndf' , SIZE = 8192KB , MAXSIZE = UNLIMITED, FILEGROWTH = 65536KB )
       LOG ON
      ( NAME = N'@Value(DatabaseName)_log', FILENAME = N'\\cifs_svm12\teal_log01\Program Files\Microsoft SQL Server\MSSQL13.MSSQLSERVER\MSSQL\Data\@Value(DatabaseName)_log.ldf' , SIZE = 335872KB , MAXSIZE = 2048GB , FILEGROWTH = 65536KB );

      ALTER DATABASE [@Value(DatabaseName)] SET COMPATIBILITY_LEVEL = 130;

      IF (1 = FULLTEXTSERVICEPROPERTY('IsFullTextInstalled'))
      begin
      EXEC [@Value(DatabaseName)].[dbo].[sp_fulltext_database] @action = 'enable'
      end;

      ALTER DATABASE [@Value(DatabaseName)] SET ANSI_NULL_DEFAULT OFF;
      ALTER DATABASE [@Value(DatabaseName)] SET ANSI_NULLS OFF;
      ALTER DATABASE [@Value(DatabaseName)] SET ANSI_PADDING OFF;
      ALTER DATABASE [@Value(DatabaseName)] SET ANSI_WARNINGS OFF;
      ALTER DATABASE [@Value(DatabaseName)] SET ARITHABORT OFF;
      ALTER DATABASE [@Value(DatabaseName)] SET AUTO_CLOSE OFF;
      ALTER DATABASE [@Value(DatabaseName)] SET AUTO_SHRINK OFF;
      ALTER DATABASE [@Value(DatabaseName)] SET AUTO_UPDATE_STATISTICS ON ;
      ALTER DATABASE [@Value(DatabaseName)] SET CURSOR_CLOSE_ON_COMMIT OFF;
      ALTER DATABASE [@Value(DatabaseName)] SET CURSOR_DEFAULT  GLOBAL;
      ALTER DATABASE [@Value(DatabaseName)] SET CONCAT_NULL_YIELDS_NULL OFF ;
      ALTER DATABASE [@Value(DatabaseName)] SET NUMERIC_ROUNDABORT OFF;
      ALTER DATABASE [@Value(DatabaseName)] SET QUOTED_IDENTIFIER OFF;
      ALTER DATABASE [@Value(DatabaseName)] SET RECURSIVE_TRIGGERS OFF ;
      ALTER DATABASE [@Value(DatabaseName)] SET  DISABLE_BROKER;
      ALTER DATABASE [@Value(DatabaseName)] SET AUTO_UPDATE_STATISTICS_ASYNC OFF ;
      ALTER DATABASE [@Value(DatabaseName)] SET DATE_CORRELATION_OPTIMIZATION OFF;
      ALTER DATABASE [@Value(DatabaseName)] SET TRUSTWORTHY OFF ;
      ALTER DATABASE [@Value(DatabaseName)] SET ALLOW_SNAPSHOT_ISOLATION OFF ;
      ALTER DATABASE [@Value(DatabaseName)] SET PARAMETERIZATION SIMPLE ;
      ALTER DATABASE [@Value(DatabaseName)] SET READ_COMMITTED_SNAPSHOT OFF ;
      ALTER DATABASE [@Value(DatabaseName)] SET HONOR_BROKER_PRIORITY OFF ;
      ALTER DATABASE [@Value(DatabaseName)] SET RECOVERY SIMPLE ;
      ALTER DATABASE [@Value(DatabaseName)] SET  MULTI_USER ;
      ALTER DATABASE [@Value(DatabaseName)] SET PAGE_VERIFY CHECKSUM  ;
      ALTER DATABASE [@Value(DatabaseName)] SET DB_CHAINING OFF ;
      ALTER DATABASE [@Value(DatabaseName)] SET FILESTREAM( NON_TRANSACTED_ACCESS = OFF ) ;
      ALTER DATABASE [@Value(DatabaseName)] SET TARGET_RECOVERY_TIME = 60 SECONDS ;
      ALTER DATABASE [@Value(DatabaseName)] SET DELAYED_DURABILITY = DISABLED ;
      ALTER DATABASE [@Value(DatabaseName)] SET QUERY_STORE = OFF;

      USE [@Value(DatabaseName)];
      ALTER DATABASE SCOPED CONFIGURATION SET LEGACY_CARDINALITY_ESTIMATION = OFF;
      ALTER DATABASE SCOPED CONFIGURATION FOR SECONDARY SET LEGACY_CARDINALITY_ESTIMATION = PRIMARY;
      ALTER DATABASE SCOPED CONFIGURATION SET MAXDOP = 0;
      ALTER DATABASE SCOPED CONFIGURATION FOR SECONDARY SET MAXDOP = PRIMARY;
      ALTER DATABASE SCOPED CONFIGURATION SET PARAMETER_SNIFFING = ON;
      ALTER DATABASE SCOPED CONFIGURATION FOR SECONDARY SET PARAMETER_SNIFFING = PRIMARY;
      ALTER DATABASE SCOPED CONFIGURATION SET QUERY_OPTIMIZER_HOTFIXES = OFF;
      ALTER DATABASE SCOPED CONFIGURATION FOR SECONDARY SET QUERY_OPTIMIZER_HOTFIXES = PRIMARY;
      ALTER DATABASE [@Value(DatabaseName)] SET  READ_WRITE;
      --
      -- Add some users and roles
      --
      create user [tableau] FOR login [tableau];
      exec sp_addrolemember 'db_datareader','tableau';

      --add  read-only credentials for EEADMZ1 users
      create user [JEDI_reader] FOR login [EEADMZ1\JEDI_reader];
      exec sp_addrolemember 'db_datareader','JEDI_reader';
    INITIATOR -> SQLExecutor_7 [INITIATOR]
Note: Configure database
SQLExecutor_7
    COMBINE_ATTRS = Result Attributes Only
    COMBINE_GEOM = Initiator Geometry Only
    DATASET = LocalJedi
    FORMAT = MSSQL_ADO
    MSSQL_ADO_APPLICATION_INTENT = ReadWrite
    MSSQL_ADO_COMMAND_TIMEOUT = 0
    MSSQL_ADO_CREATE_FEATURE_TABLES_FROM_DATA = Yes
    MSSQL_ADO_NAMED_CONNECTION = LocalJedi
    MSSQL_ADO_QUERY_FEATURE_TYPES_FOR_MERGE_FILTERS = Yes
    SQL_STATEMENT:
      FME_SQL_DELIMITER ;
      USE @Value(DatabaseName);
      -- Create an Master encryption key if that was not configred
      CREATE MASTER KEY ENCRYPTION BY PASSWORD = '!#eRdjYU87%';

      -- Add Azure storage Credentials, if not existing
      Create Database SCOPED CREDENTIAL AzureStorageCredential
          WITH IDENTITY = '@Value(DatabaseName)',
          SECRET = 'LOEJtyYZl6S0vq6/Ig2MGY213YSqfxl1kwC8yk4GE3f+0L1AwrArzfjSf5BAQOOH8R0qVnPsiSqmlcD37ktYBg==';

      --Configure Hadoop connectivity
      sp_configure @configname = 'hadoop connectivity',
                   @configvalue = 7;

      RECONFIGURE;

      -- Specify location and credential to access Azure blob storage.
      CREATE EXTERNAL DATA SOURCE AzureStorage
      WITH (
          TYPE = HADOOP,
          LOCATION= 'wasbs://cwsblob01@cwsblobstorage01.blob.core.windows.net',
          CREDENTIAL = AzureStorageCredential
      );

      CREATE EXTERNAL FILE FORMAT TextFileVerticalLineGz
      WITH (	FORMAT_TYPE = DelimitedText
                      ,FORMAT_OPTIONS (FIELD_TERMINATOR = '|')
                     ,DATA_COMPRESSION='org.apache.hadoop.io.compress.GzipCodec'
           );


      CREATE EXTERNAL FILE FORMAT TextFileVerticalLineCsv
      WITH (	FORMAT_TYPE = DelimitedText
                      ,FORMAT_OPTIONS (FIELD_TERMINATOR = '|')
           );
    INITIATOR -> Output (output)
Output (output)

FME custom transformer CompileTSQLForTable

Parameters:
- TableName =   # Table name
- CubeId =

Input (input)
    -> ParameterFetcher
ParameterFetcher
    ATTR_LIST = _TableName $(TableName) _CubeId $(CubeId)
    -> SQLExecutor [INITIATOR]
SQLExecutor
    COMBINE_ATTRS = Keep Initiator Attributes if Conflict
    COMBINE_GEOM = Initiator Geometry Only
    DATASET = CubeManager
    EXPOSED_ATTRIBUTE_LIST = Columnlength,ColumnName,ColumnScale,isnullable,TableName1,TypeName
    FORMAT = MSSQL_JDBC_NONSPATIAL
    MSSQL_JDBC_NONSPATIAL_NAMED_CONNECTION = CubeManager
    MSSQL_JDBC_NONSPATIAL_QUERY_FEATURE_TYPES_FOR_MERGE_FILTERS = Yes
    MSSQL_JDBC_NONSPATIAL_QUERY_TIMEOUT = 30
    SQL_STATEMENT:
      select
      	'@Value(_TableName)' as TableName1,
      	CubeFieldAlias as ColumnName,
      	1 as isnullable,
      	case when lower(FieldType) = 'tinyint' then 4
      		 when lower(FieldType) = 'smallint' then 4
      		 when lower(FieldType) = 'int' then 4
      		 when lower(FieldType) = 'bigint' then 8
      		 when lower(FieldType) = 'float' then 8
      		 when lower(FieldType) = 'double' then 8
      		 when lower(FieldType) = 'decimal' then 5
      		 when lower(FieldType) = 'numeric' then
      				SUBSTRING(
      				 SUBSTRING(FieldType,charindex('(', FieldType)+1,len(FieldType)),
      				 1,
      				 CHARINDEX(',',SUBSTRING(FieldType,charindex('(', FieldType)+1,len(FieldType)))-1
      				 )
      		 when lower(FieldType) = 'varbinary' then 8000
      		 when charindex('varchar',lower(FieldType)) >  0  then
      			SUBSTRING(SUBSTRING(FieldType, charindex('(', FieldType)+1 , len(FieldType)),1,len(SUBSTRING(FieldType, charindex('(', FieldType)+1 , len(FieldType)))-1)
      		when lower(FieldType) = 'text' then 8000
      		 else	255
      	end as Columnlength,
      	case when lower(FieldType) = 'tinyint' then 0
      		 when lower(FieldType) = 'smallint' then 0
      		 when lower(FieldType) = 'int' then 0
      		 when lower(FieldType) = 'bigint' then 0
      		 when lower(FieldType) = 'float' then 0
      		 when lower(FieldType) = 'double' then 0
      		 when lower(FieldType) = 'decimal' then 0
      		 when lower(FieldType) = 'numeric' then
      			SUBSTRING(
      			 SUBSTRING(FieldType,charindex(',', FieldType)+1,len(FieldType) - charindex(',', FieldType)+1  ),
      			 1,
      			 len(SUBSTRING(FieldType,charindex(',', FieldType)+1,len(FieldType) - charindex(',', FieldType)+1  ))-1
      			)
      		 else	null
      	end as ColumnScale,
      	case when
      		charindex('(', FieldType) >0 then
      		SUBSTRING(FieldType,1, charindex('(', FieldType)-1)
      	when lower(FieldType) = 'double' then 'float'
      	when lower(FieldType) = 'text' then 'varchar'
      	else
      		case
                  when isnull(AggregateFunction,'')!='' AND isnull(AggregateFunction,'')!='MODE'   then 'float'
                  else
                      case
                          when FieldType like 'bigint' then 'bigint'
                          when FieldType like '%int' then
                          'int'
                          else FieldType
                      end
                  end
      	end as TypeName

      from CubeFields inner join
      	fields on CubeFields.FieldId = Fields.FieldId inner join
      	files on Fields.FileId = files.FileId inner join
      	CubeDimensions on files.CubeDimensionId = CubeDimensions.CubeDimensionId inner join
      	GridTypes on CubeDimensions.GridTypeId = GridTypes.GridTypeId

      where
      	CubeFields.CubeId = @Value(_CubeId) and LookupFieldId IS NULL
      	and fields.IgnoreField = 0
      order by
          GridTypes.XCellSpacing,
      	--CubeFields.DimOrder,
      	fields.FieldOrder,
      	ColumnName
    RESULT -> AttributeValueMapper
AttributeValueMapper
    DEFAULT_VALUE = " "
    DIRECTION = Forward (Source To Destination)
    LUT = 1,NULL
    SRC = isnullable
    VAL_ATTR = isnullable
    -> TestFilter
Aggregator
    ACCUM_ATTRS_NAME = Get Attributes From One Representative Feature
    AGGREGATE_TYPE = Heterogeneous Collection
    CONCAT_ATTRS = TSQL_FieldName FieldListName
    GROUP_BY = TableName1
    MODE = Geometry - Assemble One Level
    ORDERED = No
    SEP = |
    AGGREGATE -> StringReplacer
StringReplacer
    CASE = NO
    FIND_TEXT = |
    NO_MATCH = _FME_NO_OP_
    REGEXP = NO
    REPLACE_TEXT = ",\n    "
    SRC_ATTRS = TSQL_FieldName,FieldListName
    -> TableNameFilter
TableNameFilter: TestFilter
    DEFAULT_VALUE = <UNFILTERED>
    TEST_LIST = "BOOL_OP,OR,COMPOSITE_TEST,""""""1"""""",TEST_CLAUSE,CASE_INSENSITIVE_TEST @Value(_TableName) BEGINS_WITH C_",C_Table,"BOOL_OP,OR,COMPOSITE_TEST,""""""1"""""",TEST_CLAUSE,CASE_INSENSITIVE_TEST @Value(_TableName) BEGINS_WITH F_",F_Table
    C_Table -> AddCTableFields
    F_Table -> AddFTableFields
AddCTableFields: AttributeCreator
    ATTR_TABLE:
      SET_TO TSQL_FieldName = @Value(TSQL_FieldName),
        AreaHa float null
      SET_TO FieldListName = @Value(FieldListName),
        AreaHa
    -> Output (output)
AddFTableFields: AttributeCreator
    ATTR_TABLE:
      SET_TO TSQL_FieldName = GridNum10km bigint null,
        GridNum bigint null,
        @Value(TSQL_FieldName),
        longitude float null,
        latitude float null,
        AreaHa float null
      SET_TO FieldListName = GridNum10km,
        GridNum,
        @Value(FieldListName),
        longitude,
        latitude,
        AreaHa
    -> Output (output)
Output (output)

Bookmark: ATTRIBUTE TYPE REDEFINED
TestFilter
    DEFAULT_VALUE = Basic
    TEST_LIST = "BOOL_OP,OR,COMPOSITE_TEST,""""""1"""""",TEST_CLAUSE,TEST @Value(TypeName) = text",text,BOOL_OP,OR,COMPOSITE_TEST,<Unused>,TEST_CLAUSE,"TEST @Value(TypeName) = nvarchar",nvarchar,BOOL_OP,OR,COMPOSITE_TEST,<Unused>,TEST_CLAUSE,"TEST @Value(TypeName) = varchar",varchar,BOOL_OP,OR,COMPOSITE_TEST,<Unused>,TEST_CLAUSE,"TEST @Value(TypeName) = varbinary",varbinary,BOOL_OP,OR,COMPOSITE_TEST,<Unused>,TEST_CLAUSE,"TEST @Value(TypeName) = numeric",numeric
    text -> AttributeCreator
    nvarchar -> AttributeCreator
    varchar -> AttributeCreator_3
    varbinary -> AttributeCreator_3
    numeric -> AttributeCreator_4
    Basic -> AttributeCreator_2
AttributeCreator
    ATTR_TABLE:
      SET_TO TSQL_FieldName = [@Value(ColumnName)] [@Value(TypeName)] (@Evaluate(@Value(Columnlength)/2)) @Value(isnullable)
      SET_TO FieldListName = [@Value(ColumnName)]
    -> Aggregator
AttributeCreator_3
    ATTR_TABLE:
      SET_TO TSQL_FieldName = [@Value(ColumnName)] [@Value(TypeName)] (@Value(Columnlength)) @Value(isnullable)
      SET_TO FieldListName = [@Value(ColumnName)]
    -> Aggregator
AttributeCreator_4
    ATTR_TABLE:
      SET_TO TSQL_FieldName = FME_CONDITIONAL:DEFAULT_VALUE'[@Value(ColumnName)] [real] @Value(isnullable)'BOOL_OP;OR;COMPOSITE_TEST;<Unused>;TEST @Value(ColumnScale) = 0'[@Value(ColumnName)] [bigint] @Value(isnullable)'FME_NUM_CONDITIONS2___
      SET_TO FieldListName = [@Value(ColumnName)]
    -> Aggregator
AttributeCreator_2
    ATTR_TABLE:
      SET_TO TSQL_FieldName = [@Value(ColumnName)] [@Value(TypeName)] @Value(isnullable)
      SET_TO FieldListName = [@Value(ColumnName)]
    -> Aggregator

FME custom transformer CreateCubeTable

Parameters:
- TableName =
- DatabaseName =
- CubeId =

Input (input)
    -> ParameterFetcher
ParameterFetcher
    ATTR_LIST = TableName $(TableName) DatabaseName $(DatabaseName) CubeId $(CubeId)
    -> CompileTSQLForTable_2
Note: Compile a CREATE TABLE TSQL / and Field list in the same order
CompileTSQLForTable_2
    CubeId = @Value(CubeId)
    TableName = @Value(TableName)
    -> AttributeCreator_40
    -> SQLExecutor_9 [INITIATOR]
    -> Inspector
AttributeCreator_40
    ATTR_TABLE:
      SET_TO TransformerPath = CompileTSQLForTable
      SET_TO MessageString = Compile a create table TSQL and fields in the same order
    -> AttributeCreator_20_OUTPUT_-__AttributeCreator_INFO_3
Note: Create external table in EEA´s Local SQL Server / (map the blob files to a table in SQL server)
SQLExecutor_9
    COMBINE_ATTRS = Result Attributes Only
    COMBINE_GEOM = Initiator Geometry Only
    DATASET = LocalJedi
    FORMAT = MSSQL_ADO
    MSSQL_ADO_APPLICATION_INTENT = ReadWrite
    MSSQL_ADO_COMMAND_TIMEOUT = 14000
    MSSQL_ADO_CREATE_FEATURE_TABLES_FROM_DATA = Yes
    MSSQL_ADO_NAMED_CONNECTION = LocalJedi
    MSSQL_ADO_QUERY_FEATURE_TYPES_FOR_MERGE_FILTERS = Yes
    SQL_STATEMENT:
      FME_SQL_DELIMITER ;
      USE @Value(DatabaseName);

      if exists (select top 1 name from sysobjects where name = '@Value(TableName)_External' and xtype = 'ET')
      	DROP EXTERNAL TABLE dbo.[@Value(TableName)_External];

      -- CREATE EXTERNAL TABLE based on the FME information
      CREATE EXTERNAL TABLE dbo.[@Value(TableName)_External] (
      	@Value(TSQL_FieldName)
      )
      WITH (
      	LOCATION = 'ExportTable\@Value(TableName)\',
      	DATA_SOURCE= AzureStorage,
      	FILE_FORMAT= TextFileVerticalLineGz,
          REJECT_TYPE=value,
          REJECT_VALUE=1
      );
    INITIATOR -> FeatureHolder_2
    INITIATOR -> AttributeCreator_42
    <REJECTED> -> AttributeCreator_31
AttributeCreator_42
    ATTR_TABLE:
      SET_TO TransformerPath = SQLExecutor
      SET_TO MessageString = Create external table in Local SQL Server 2016
        (map the blob files to a table in SQL server)
    -> AttributeCreator_20_OUTPUT_-__AttributeCreator_INFO_3
Note: INFO
AttributeCreator_20_OUTPUT_-__AttributeCreator_INFO_3: Junction
    -> Junction_2
Junction_2
    -> Info_1 (output)
Info_1 (output)
Note: Make sure we export everything / before we import...
FeatureHolder_2
    -> SQLExecutor_10 [INITIATOR]
AttributeCreator_43
    ATTR_TABLE:
      SET_TO TransformerPath = SQLExecutor_2
      SET_TO MessageString = Import into a local SQL Server 2016 table
    -> Junction
AttributeCreator_44
    ATTR_TABLE:
      SET_TO TransformerPath = SQLExecutor_3
      SET_TO MessageString = Create cluster columnstore index
    -> Junction
AttributeCreator_45
    ATTR_TABLE:
      SET_TO TransformerPath = DROPEXTERNALTABLE\SQLExecutor_4
      SET_TO MessageString = Drop external table success
    -> Junction
Junction
    -> Info_2 (output)
Info_2 (output)
SQLExecutor_12_Initiator (output)
AttributeCreator_31
    ATTR_TABLE:
      SET_TO MessageString = Failed to create External table inside the local database towards blob folder
      SET_TO TransformerPath = SQLExecutor
    -> Junction_4
Junction_4
    -> Error (output)
Error (output)
Inspector [off]

Bookmark: CREATE TABLE IN JEDI_<CubeName>
Note: Import into a local SQL Server 2016 table
SQLExecutor_10
    COMBINE_ATTRS = Result Attributes Only
    COMBINE_GEOM = Initiator Geometry Only
    DATASET = LocalJedi
    FORMAT = MSSQL_ADO
    MSSQL_ADO_APPLICATION_INTENT = ReadWrite
    MSSQL_ADO_COMMAND_TIMEOUT = 14000
    MSSQL_ADO_CREATE_FEATURE_TABLES_FROM_DATA = Yes
    MSSQL_ADO_NAMED_CONNECTION = LocalJedi
    MSSQL_ADO_QUERY_FEATURE_TYPES_FOR_MERGE_FILTERS = Yes
    SQL_STATEMENT:
      FME_SQL_DELIMITER ;
      USE @Value(DatabaseName);

      if exists (select top 1 name from sysobjects where name = '@Value(TableName)' and xtype = 'U')
      	DROP TABLE dbo.[@Value(TableName)];

      SELECT
          @Value(FieldListName)
      INTO [@Value(TableName)]
      FROM [@Value(TableName)_External];
    INITIATOR -> SQLExecutor_11 [INITIATOR]
    INITIATOR -> AttributeCreator_43
    <REJECTED> -> AttributeCreator_30
Note: Create cluster columnstore index
SQLExecutor_11
    COMBINE_ATTRS = Result Attributes Only
    COMBINE_GEOM = Initiator Geometry Only
    DATASET = LocalJedi
    FORMAT = MSSQL_ADO
    MSSQL_ADO_APPLICATION_INTENT = ReadWrite
    MSSQL_ADO_COMMAND_TIMEOUT = 14000
    MSSQL_ADO_CREATE_FEATURE_TABLES_FROM_DATA = Yes
    MSSQL_ADO_NAMED_CONNECTION = LocalJedi
    MSSQL_ADO_QUERY_FEATURE_TYPES_FOR_MERGE_FILTERS = Yes
    SQL_STATEMENT:
      FME_SQL_DELIMITER ;

      USE @Value(DatabaseName);

      CREATE CLUSTERED COLUMNSTORE INDEX [ClusteredColumnStoreIndex-@Value(TableName)]
      	ON [dbo].[@Value(TableName)]
      	WITH (DROP_EXISTING = OFF, COMPRESSION_DELAY = 0) ON [PRIMARY];
    INITIATOR -> SQLExecutor_12 [INITIATOR]
    INITIATOR -> AttributeCreator_44
    <REJECTED> -> AttributeCreator_33
AttributeCreator_33
    ATTR_TABLE:
      SET_TO MessageString = Failed to create cluster columnstore index
      SET_TO TransformerPath = SQLExecutor_3
    -> Junction_4
AttributeCreator_30
    ATTR_TABLE:
      SET_TO MessageString = Failed to import from External Table towards real SQL table.
      SET_TO TransformerPath = SQLExecutor_2
    -> Junction_4

Bookmark: DROP EXTERNAL TABLE
Note: Drop external table
SQLExecutor_12
    COMBINE_ATTRS = Result Attributes Only
    COMBINE_GEOM = Initiator Geometry Only
    DATASET = LocalJedi
    FORMAT = MSSQL_ADO
    MSSQL_ADO_APPLICATION_INTENT = ReadWrite
    MSSQL_ADO_COMMAND_TIMEOUT = 14000
    MSSQL_ADO_CREATE_FEATURE_TABLES_FROM_DATA = Yes
    MSSQL_ADO_NAMED_CONNECTION = LocalJedi
    MSSQL_ADO_QUERY_FEATURE_TYPES_FOR_MERGE_FILTERS = Yes
    SQL_STATEMENT:
      FME_SQL_DELIMITER ;

      USE @Value(DatabaseName);

      -- DROP EXTERNAL TABLE If it extists
      if exists (select top 1 name from sysobjects where name = '@Value(TableName)_External' and xtype = 'ET')
      	DROP EXTERNAL TABLE dbo.[@Value(TableName)_External];
    INITIATOR -> AttributeCreator_45
    INITIATOR -> SQLExecutor_12_Initiator (output)
    <REJECTED> -> AttributeCreator_34
AttributeCreator_34
    ATTR_TABLE:
      SET_TO MessageString = Failed to drop external table dbo.[@Value(TableName)_External]
      SET_TO TransformerPath = SQLExecutor_4
    -> Junction_4
