FME workspace DimensionFilesToAzureDatabricks.fmw
Title: StoreCubeSourceFilesToAzure
Description: Will upload the dimension files (.CSV-File) into the cloud. (JEDI-Application)
Usage: This script will upload dimensions files from the JEDI-System into the Azure cloud so we can import the records inside SQL Datawarehouse.
Each file takes about 5 minutes to upload. Dimension files must be .csv and compressed as .gz and contain only \n as record seperators. The fields must be double quoted.
The headers are double checked inside the database and ensured that they contain the correct order as configured inside the dimension file. 
Note that SQL Datawarehouse does not expect any field header file. Because of that we expect a folder that minimum contains two files. 
The .csv.gz file containing the data.
The .header file containing the fieldnames comma seperated. (Only the first line will be interpreted!)
History: 05/07/2016,Jan Bliki,Initial creation,16/09/2016,Jan Bliki,Moved to .gz files and a folder structure for each individual file.

Parameters:
- FileId =

Note: dbo.[Files].[Validated]=1 / and dbo.[Files].[AzureDimensionFile] is null / and dbo.[Files].[DimensionFile] is not null
SQLCreator
    DATASET = CubeManager
    EXPOSED_ATTRIBUTE_LIST = AzureDimensionFile AzureDimensionUploaded DimensionFile DimensionFileCreated ErrorMessages FileId FMEJobIdDimensionUploaded Name GridTypesShortName
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = CubeManager
    MSSQL_ADO_QUERY_FEATURE_TYPES_FOR_MERGE_FILTERS = Yes
    SQL_STATEMENT:
      select   dbo.[CubeDimensions].[Name]
              ,GridTypes.name as GridTypesShortName
              ,dbo.[Files].[FileId]
              ,dbo.[Files].[DimensionFile]
              ,dbo.[Files].[DimensionFileCreated]
              ,dbo.[Files].[ErrorMessages]
              ,dbo.[Files].[AzureDimensionFile]
              ,dbo.[Files].[AzureDimensionUploaded]
      from dbo.[CubeDimensions]
      inner join dbo.[Files] on dbo.[Files].[CubeDimensionId] = dbo.[CubeDimensions].[CubeDimensionId]
      inner join GridTypes on GridTypes.GridTypeId = Cubedimensions.GridTypeId
      where dbo.[Files].[Validated]=1
          and fileId=$(FileId)
    RESULT -> AttributeCreator_17
    <REJECTED> -> AttributeCreator_8
CleanUpBlob
    AZUREDIMENSIONFILE = @Value(AzureDimensionFile)
    FILEID = @Value(FileId)
    NAME = @Value(Name)
    Initiator -> TempPathnameCreator_2
Aggregator_4
    ACCUM_ATTRS_NAME = Drop Incoming Attributes
    GROUP_BY = FileId _pathname
    MODE = Attributes Only
    ORDERED = No
    SEP = ,
    AGGREGATE -> AttributeCreator_15
    AGGREGATE -> FileSystemDeleteMoveCopyExist_3 [FileName]
AttributeCreator_15
    ATTR_TABLE:
      SET_TO TransformerPath = CLEAN_UP_TEMP_FOLDER
      SET_TO MessageString = Clean temp folder, remove or not found
      SET_TO FileId = $(FileId)
    -> AttributeCreator_11_OUTPUT_-__AttributeCreator_INFO
FileSystemDeleteMoveCopyExist_3
    Action = RMDIR
    FILEINPUT = @Value(_pathname)
AttributeCreator_9
    ATTR_TABLE:
      SET_TO TransformerPath = CubeManager-DB_FILE_STATUS\SQLExecutor_3
      SET_TO MessageString = Error: @Value(_reader_error).
        WorkSpace: $(WORKSPACE_NAME)
        Transformer name: SQLExecutor_3
    -> AttributeCreator_ERROR
Aggregator
    ACCUM_ATTRS_NAME = Drop Incoming Attributes
    GROUP_BY = FileId
    MODE = Attributes Only
    ORDERED = No
    SEP = ,
    AGGREGATE -> AttributeCreator_16
AttributeCreator_16
    ATTR_TABLE:
      SET_TO TransformerPath = STORE_ATTRIBUTE_ORDER\SQLExecutor
      SET_TO MessageString = Update field order inside "dbo.fields" table
    -> AttributeCreator_11_OUTPUT_-__AttributeCreator_INFO
AttributeCreator_7
    ATTR_TABLE:
      SET_TO TransformerPath = STORE_ATTRIBUTE_ORDER\SQLExecutor
      SET_TO MessageString = Error: @Value(_reader_error).
        WorkSpace: $(WORKSPACE_NAME)
        Transformer name: SQLExecutor
    -> AttributeCreator_ERROR
AttributeCreator_12
    ATTR_TABLE:
      SET_TO TransformerPath = STORE_ATTRIBUTE_ORDER\ListExploder
      SET_TO MessageString = Error: List Exploder Error.
        WorkSpace: $(WORKSPACE_NAME)
        Transformer name: ListExploder
    -> AttributeCreator_ERROR
AttributeCreator_6
    ATTR_TABLE:
      SET_TO TransformerPath = STORE_ATTRIBUTE_ORDER\FeatureReader
      SET_TO MessageString = Error: @Value(_reader_error).
        WorkSpace: $(WORKSPACE_NAME)
        Transformer name: FeatureReader
    -> AttributeCreator_ERROR
Aggregator_2
    ACCUM_ATTRS_NAME = Drop Incoming Attributes
    GROUP_BY = FileId
    MODE = Attributes Only
    ORDERED = No
    SEP = ,
    AGGREGATE -> AttributeCreator_11
AttributeCreator_11
    ATTR_TABLE:
      SET_TO TransformerPath = READ_LOCAL_FOLDER
      SET_TO MessageString = Read local folder Success
    -> AttributeCreator_11_OUTPUT_-__AttributeCreator_INFO
AttributeCreator_11_OUTPUT_-__AttributeCreator_INFO: Junction
    -> AttributeCreator_INFO
AttributeCreator_INFO
    ATTR_TABLE = SET_TO MessageType = INFO
    -> AttributeKeeper
AttributeCreator_2
    ATTR_TABLE:
      SET_TO TransformerPath = READ_LOCAL_FOLDER
      SET_TO MessageString = Error: @Value(_reader_error).
        WorkSpace: $(WORKSPACE_NAME)
        Transformer name: FeatureReader_2
    -> AttributeCreator_ERROR
AttributeCreator_18
    ATTR_TABLE:
      SET_TO TransformerPath = SQLExecutor_4
      SET_TO MessageString = Error: @Value(_reader_error).
        WorkSpace: $(WORKSPACE_NAME)
        Transformer name:  SQLExecutor_4
    -> AttributeCreator_ERROR
AttributeCreator_ERROR
    ATTR_TABLE = SET_TO MessageType = ERROR
    -> AttributeKeeper
AttributeKeeper
    CREATE_BULK_MODE_FEATURES = No
    KEEP_ATTRS = TransformerPath,FileId,MessageString,MessageType
    -> JediLogWritter
JediLogWritter
    FILEID = @Value(FileId)
    MESSAGESTRING = @Value(MessageString)
    MESSAGETYPE = @Value(MessageType)
    OBJECTPROCESSED = Dimension
    SQLServerConn = CubeManager
    TRANSFORMERPATH = $(WORKSPACE_NAME)\STEP3: UPLOAD GRID\@Value(TransformerPath)
    -> Tester
Tester
    BOOL_OP = OR
    TEST_CLAUSE = TEST @Value(MessageType) = ERROR
    TEST_MODE = TEST
AttributeCreator_8
    ATTR_TABLE:
      SET_TO TransformerPath = SQL_Creator
      SET_TO MessageString = Error: @Value(_reader_error).
        WorkSpace: $(WORKSPACE_NAME)
        Transformer name:  SQLExecutor_4

Bookmark: Tell DB we are executing the job
Note: Reset the database and provide the job_id so log information can be found easily.
AttributeCreator_17
    ATTR_TABLE = SET_TO _FME_JOB_ID = FME_CONDITIONAL:DEFAULT_VALUE'$(FME_JOB_ID)'BOOL_OP;AND;COMPOSITE_TEST;<Unused>;TEST $(FME_JOB_ID) ATTRIBUTE_IS_MISSING _FME_BLANK_STRING_;TEST $(FME_JOB_ID) NOT_ATTRIBUTE_HAS_VALUE _FME_BLANK_STRING_'-1'FME_NUM_CONDITIONS2___
    -> SQLExecutor_4 [INITIATOR]
SQLExecutor_4
    COMBINE_ATTRS = Result Attributes Only
    COMBINE_GEOM = Initiator Geometry Only
    DATASET = CubeManager
    FORMAT = MSSQL_ADO
    MSSQL_ADO_COMMAND_TIMEOUT = 30
    MSSQL_ADO_NAMED_CONNECTION = CubeManager
    MSSQL_ADO_QUERY_FEATURE_TYPES_FOR_MERGE_FILTERS = Yes
    SQL_STATEMENT:
      update dbo.[Files]
          set FMEJobIdDimensionUploaded = @Value(_FME_JOB_ID)
       where fileId = @Value(FileId)
    INITIATOR -> CleanUpBlob
    <REJECTED> -> AttributeCreator_18

Bookmark: Create temp folder to copy UUID files
TempPathnameCreator_2
    PATHNAME_ATTR = _pathname
    -> FileSystemDeleteMoveCopyExist_2 [FileName]
FileSystemDeleteMoveCopyExist_2
    Action = MKDIR
    FILEINPUT = @Value(_pathname)
    Success -> FeatureReader_2 [INITIATOR]

Bookmark: READ LOCAL FOLDER
FeatureReader_2
    ATTR_ACCUM_MODE = Merge Initiator and Result
    ATTR_CONFLICT_RES = Use Result
    COMBINE_GEOM = Use Result
    DATASET = @Value(DimensionFile)
    FORMAT = PATH
    OUTPUT_FEATURES_DISPLAY = Schema and Data Features
    PATH_GLOB_PATTERN = *
    PATH_RETRIEVE_FILE_PROPERTIES = NO
    PATH_TYPE = FILE
    <OTHER> -> AttributeExposer
    <OTHER> -> Aggregator_2
    <REJECTED> -> AttributeCreator_2

Bookmark: COMPILE DimensionFile
AttributeExposer
    ATTR_LIST = path_directory_windows,path_filename
    -> AttributeCreator_4
AttributeCreator_4
    ATTR_TABLE = SET_TO DimensionFile = @Value(path_directory_windows)@Value(path_filename)
    -> TestFilter_2
TestFilter_2
    DEFAULT_VALUE = DimensionFile
    TEST_LIST = BOOL_OP,OR,COMPOSITE_TEST,<Unused>,TEST_CLAUSE,"TEST @Value(DimensionFile) ENDS_WITH .fieldnames",HeaderFile
    HeaderFile -> Sampler_2
    DimensionFile -> AttributeCreator_3

Bookmark: EXTRACT DATE
AttributeCreator_3
    ATTR_TABLE = SET_TO __DimensionDate = @Value(DimensionFileCreated)
    -> DateFormatter
DateFormatter
    DATE_ATTR = __DimensionDate
    FMT = %Y_%m_%d
    INVALID_DATE_VALUE = _FME_NO_OP_
    SRCFMT = %Y%m%d%H%M%S.000
    -> FilenamePartExtractor

Bookmark: BLOB FOLDER NAME
FilenamePartExtractor
    EXTENSION_ATTR = _extension
    ROOTNAME_ATTR = _filename
    SRC_ATTR = @Value(DimensionFile)
    -> AttributeCreator
AttributeCreator
    ATTR_TABLE = SET_TO AzureDimensionFile = Dimensions/@Value(Name)_@Value(FileId)
    -> MultiAzureUpload

Bookmark: UPLOAD TO AZURE
MultiAzureUpload
    AZUREDIMENSIONFILE = @Value(AzureDimensionFile)
    DIMENSIONFILE = @Value(DimensionFile)
    _PATHNAME = @Value(_pathname)
    Success -> FeatureHolder
    Success -> Aggregator_3
    Failed -> StringReplacer

Bookmark: CubeManager-DB FILE STATUS
Note: Set attributes in database (Files-table) express that all files have been processed.
FeatureHolder
    -> Sampler
    -> TestFilter_3
Sampler
    RATE = 1
    SAMPLE_MODE = No
    SAMPLE_TYPE_LONG = First N Features
    SAMPLED -> SQLExecutor_3 [INITIATOR]
SQLExecutor_3
    COMBINE_ATTRS = Result Attributes Only
    COMBINE_GEOM = Initiator Geometry Only
    DATASET = CubeManager
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = CubeManager
    MSSQL_ADO_QUERY_FEATURE_TYPES_FOR_MERGE_FILTERS = Yes
    SQL_STATEMENT:
      update dbo.[Files]
          set FMEJobIdDimensionUploadedStatus = 1,
              AzureDimensionFile = 'Dimensions/@Value(Name)_@Value(FileId)',
              AzureDimensionUploaded=getdate()
       where fileId = @Value(FileId)
    INITIATOR -> AttributeCreator_14
    <REJECTED> -> AttributeCreator_9
Aggregator_3
    ACCUM_ATTRS_NAME = Drop Incoming Attributes
    GROUP_BY = FileId
    MODE = Attributes Only
    ORDERED = No
    SEP = ,
    AGGREGATE -> AttributeCreator_13
AttributeCreator_13
    ATTR_TABLE:
      SET_TO TransformerPath = UPLOAD TO AZURE
      SET_TO MessageString = We use multi processing so we can have more then one file uploaded to the cloud at the same time.
    -> AttributeCreator_11_OUTPUT_-__AttributeCreator_INFO

Bookmark: CLEAN UP TEMP FOLDER
Note: Remove Dimension file from the local temp folder...
TestFilter_3
    DEFAULT_VALUE = <UNFILTERED>
    TEST_LIST = BOOL_OP,OR,COMPOSITE_TEST,<Unused>,TEST_CLAUSE,"TEST @Value(DimensionFile) ATTRIBUTE_HAS_VALUE """"",Delete file
    Delete file -> FileSystemDeleteMoveCopyExist [FileName]
FileSystemDeleteMoveCopyExist
    Action = DELETE
    FILEINPUT = @Value(DimensionFile)
    Success -> Aggregator_4
    Failed -> AttributeCreator_10
AttributeCreator_10
    ATTR_TABLE:
      SET_TO TransformerPath = CLEAN_UP_TEMP_FOLDER
      SET_TO MessageString = Cannot delete file
      SET_TO FileId = $(FileId)
    -> AttributeCreator_ERROR
AttributeCreator_14
    ATTR_TABLE:
      SET_TO TransformerPath = CubeManager-DB_FILE_STATUS\SQLExecutor_3
      SET_TO MessageString = Update Field FMEJobIdDimensionUploadedStatus
    -> AttributeCreator_11_OUTPUT_-__AttributeCreator_INFO

Bookmark: ERROR MESSAGING
StringReplacer
    CASE = NO
    FIND_TEXT = '
    NO_MATCH = _FME_NO_OP_
    REGEXP = NO
    REPLACE_TEXT = ''
    SRC_ATTRS = ErrorMessages
    -> AttributeCreator_5
AttributeCreator_5
    ATTR_TABLE:
      SET_TO TransformerPath = ERROR_MESSAGING
      SET_TO MessageString = Failed Uploading file to blob @Value(DimensionFile)
      SET_TO MessageType = WARNING
    -> AttributeKeeper

Bookmark: STORE ATTRIBUTE ORDER
Note: We asume all files have the same header and this is important as all files get imported into one single table.
Sampler_2
    RATE = 1
    SAMPLE_MODE = No
    SAMPLE_TYPE_LONG = First N Features
    SAMPLED -> FeatureReader [INITIATOR]
Note: Read the header file
FeatureReader
    ATTRIBUTES = text_line,"text_line_data,fme_geometry{0}"
    ATTR_ACCUM_MODE = Merge Initiator and Result
    ATTR_CONFLICT_RES = Use Result
    COMBINE_GEOM = Use Result
    DATASET = @Value(DimensionFile)
    FORMAT = TEXTLINE
    MAX_FEATURES = 1
    OUTPUT_FEATURES_DISPLAY = Data Features
    TEXTLINE_READ_BOTTOM_UP = No
    TEXTLINE_READ_WHOLE_FILE_AT_ONCE = NO
    TEXTLINE_SKIP_FOOTER = 0
    TEXTLINE_SKIP_LINES = 0
    text_line -> AttributeSplitter
    <REJECTED> -> AttributeCreator_6
AttributeSplitter
    ATTR_NAME = text_line_data
    DELIMITER = ,
    DROP_EMPTY_PARTS = No
    LIST_NAME = _FieldNames
    TRIM_OPTION = Both
    -> ListExploder
ListExploder
    ATTR_ACCUM_MODE = Merge Incoming List
    ATTR_CONFLICT_RES = Use Incoming List
    INDEX_ATTR = FieldOrder
    LIST_ATTR = _FieldNames{}
    ELEMENTS -> SQLExecutor [INITIATOR]
    <REJECTED> -> AttributeCreator_12
Note: Update field order / inside "dbo.fields" table
SQLExecutor
    COMBINE_ATTRS = Result Attributes Only
    COMBINE_GEOM = Initiator Geometry Only
    DATASET = CubeManager
    FORMAT = MSSQL_ADO
    MSSQL_ADO_COMMAND_TIMEOUT = 30
    MSSQL_ADO_NAMED_CONNECTION = CubeManager
    MSSQL_ADO_QUERY_FEATURE_TYPES_FOR_MERGE_FILTERS = Yes
    SQL_STATEMENT:
      UPDATE dbo.[Fields]
          set [FieldOrder] = @Value(FieldOrder)
      where [FieldName] = '@Value(_FieldNames)'
        and [FileId] = @Value(FileId)
    INITIATOR -> Aggregator
    <REJECTED> -> AttributeCreator_7

FME custom transformer FileSystemDeleteMoveCopyExist
This transformer can "move","copy","delete" files. Can as well check if a file "exist" and create or delete folders.
action:The action you like to perform. 
    fileInput: provide the input file path.
    fileOutput: provide the output file path. (Is not used when you delete or test the existance of a file)

Parameters:
- Action =
- FILEINPUT =
- FILEOUTPUT =

FileName (input)
    -> ParameterFetcher
ParameterFetcher
    ATTR_LIST = action {$(Action)} fileInput {$(FILEINPUT)} fileOutput {$(FILEOUTPUT)}
    -> PythonCaller
PythonCaller
    NEW_ATTRIBUTES = "_status "
    PYTHONSOURCE:
      import fmeobjects
      # Template Function interface:
      def processFeature(feature):
          pass

      # Template Class Interface:
      class FeatureProcessor(object):
          def __init__(self):
              pass
          def input(self,feature):
              import os,shutil

              # define and get parameters
              self._status=''
              self._fileInput = feature.getAttribute('fileInput')
              self._fileOutput = feature.getAttribute('fileOutput')
              self._action = feature.getAttribute('action')

              # When action is "delete"
              if (self._action.upper() == "DELETE"):
                  if os.path.exists(self._fileInput):
                      os.remove(self._fileInput)
                      self._status='deleted'
                  else:
                      self._status='notexist:' + self._fileInput

              # When action is "delete folder"
              if (self._action.upper() == "RMDIR"):
                  if os.path.exists(self._fileInput):
                      shutil.rmtree(self._fileInput)
                      self._status='deleted'
                  else:
                      self._status='notexist:' + self._fileInput

              # When action is "copy"
              if (self._action.upper() == "COPY"):
                  if os.path.exists(self._fileInput):
                      shutil.copy(self._fileInput,self._fileOutput)
                      self._status='copied'
                  else:
                      self._status='notexist:' + self._fileInput

              # When action is "move"
              if (self._action.upper() == "MOVE"):
                  if os.path.exists(self._fileInput):
                      shutil.move(self._fileInput,self._fileOutput)
                      self._status='moved'
                  else:
                      self._status='notexist:' + self._fileInput

              # When action is " mkdir"
              if (self._action.upper() == "MKDIR"):
                  if os.path.exists(self._fileInput):
                      self._status='created'
                  else:
                      os.makedirs(self._fileInput)
                      self._status='created'

              # When action is "exist"
              if (self._action.upper() == "EXIST"):
                  if os.path.exists(self._fileInput):
                      self._status='exist'
                  else:
                      self._status='notexist:' + self._fileInput

              feature.setAttribute('_status',self._status)
              self.pyoutput(feature)
          def close(self):
              pass
    PYTHONSYMBOL = FeatureProcessor
    -> TestFilter
TestFilter
    DEFAULT_VALUE = Failed
    TEST_LIST:
      BOOL_OP,OR,COMPOSITE_TEST,<Unused>,TEST_CLAUSE,"TEST @Value(_status) = deleted
      TEST @Value(_status) = copied
      TEST @Value(_status) = moved
      TEST @Value(_status) = exist
      TEST @Value(_status) = created",Success,BOOL_OP,OR,COMPOSITE_TEST,<Unused>,TEST_CLAUSE,"TEST @Value(_status) BEGINS_WITH notexist:",DoesNotExist
    Success -> Success (output)
    DoesNotExist -> NotFound (output)
    Failed -> Failed (output)
Success (output)
NotFound (output)
Failed (output)

FME custom transformer AzureBlobUploader
Uploads a file to Azure using the Azure Blob Service REST API (https://msdn.microsoft.com/en-us/library/azure/dd135733.aspx)
A key is needed as well as the name of the storage account.
Source data can be either from an attribute or a filepath.
Maximum file size is roughly 195 GB. 
Files larger than 64 MB will be uploaded in chunks of 4 MB.
Storage account: 
Provide the storage account. Look for this under the portal.azure.com.
Access key: 
Provide the access key for the blob inside Azure. You can find this when you select the storage inside the protal.azure.com website, go to settings and then search for "Access keys".
Use access keys to authenticate your applications when making requests to this Azure storage account. Store your access keys securely - for example, using Azure Key Vault - and don't share them. We recommend regenerating your access keys regularly. You are provided two access keys so that you can maintain connections using one key while regenerating the other. 
Container name: 
The storage countainer name. These are listed directly under the storage account pannel. 
Blob name: 
The name of the blob you are about to create. The filename of the source data will be used if this was not provided. You can create folders by simply using the '/' for example "folder1/folder2/blobname". 
Upload from: 
Describes what is provided inside the "source data" attribute. When set to "AttributeValue" it means that the source data is a binary file. When set to "file" it means that the source data is a path towards a file.
This transformer currently only stores "block blobs"
block blob: 
Block blobs let you upload large blobs efficiently. Block blobs are comprised of blocks, each of which is identified by a block ID. You create or modify a block blob by writing a set of blocks and committing them by their block IDs. Each block can be a different size, up to a maximum of 4 MB, and a block blob can include up to 50,000 blocks. The maximum size of a block blob is therefore slightly more than 195 GB (4 MB X 50,000 blocks). If you are writing a block blob that is no more than 64 MB in size, you can upload it in its entirety with a single write operation
append blob:
An append blob is comprised of blocks and is optimized for append operations. When you modify an append blob, blocks are added to the end of the blob only, via the Append Block operation. Updating or deleting of existing blocks is not supported. Unlike a block blob, an append blob does not expose its block IDs. 
Each block in an append blob can be a different size, up to a maximum of 4 MB, and an append blob can include up to 50,000 blocks. The maximum size of an append blob is therefore slightly more than 195 GB (4 MB X 50,000 blocks).
page blob:
Page blobs are a collection of 512-byte pages optimized for random read and write operations. To create a page blob, you initialize the page blob and specify the maximum size the page blob will grow. To add or update the contents of a page blob, you write a page or pages by specifying an offset and a range that align to 512-byte page boundaries. A write to a page blob can overwrite just one page, some pages, or up to 4 MB of the page blob. Writes to page blobs happen in-place and are immediately committed to the blob. The maximum size for a page blob is 1 TB. 
Request Headers: Additional headers that should be used when sending the request.
Selected attributes will be used to build the headers, example:
If selected attributes are 
Content-Encoding
Content-Type
x-ms-blob-content-disposition
and the feature entering the transformer have these attributes, something like this would be added to the headers used in the request:
x-ms-blob-content-disposition: attachment; filename=thedata.txt;
Content-Type: text/plain; charset=UTF-8
Content-Encoding: UTF-8
See also: https://docs.microsoft.com/en-us/rest/api/storageservices/fileservices/put-blob

Parameters:
- ACCOUNT =
- BLOB_NAME =
- CONTAINER =
- KEY =
- SRC_DATA =
- SRC_TYPE =
- XTRA_HEADERS =
- _PATHNAME =

Input (input)
    -> ParameterFetcher
ParameterFetcher
    ATTR_LIST = _azure_blob_uploader_headers {$(XTRA_HEADERS)}
    -> Tester
Tester
    BOOL_OP = OR
    TEST_CLAUSE = TEST @Value(_azure_blob_uploader_headers) ATTRIBUTE_HAS_VALUE ""
    TEST_MODE = TEST
    PASSED -> StringSearcher
    FAILED -> FetchParamsAttributeCreator
StringSearcher
    CASE = no
    MATCHED_PARTS_ATTR = _azure_blob_uploader_header_attributes
    MATCHED_RESULT_ATTR = _first_match
    REGEXP = (?:^|,)(?=[^"]|(")?)"?((?(1)[^"]*|[^,"]*))"?(?=,|$)
    STRING_TO_SEARCH = @Value(_azure_blob_uploader_headers)
    MATCHED -> FetchParamsAttributeCreator
    NOT_MATCHED -> AttributeRemover_2
FetchParamsAttributeCreator: AttributeCreator
    ATTR_TABLE:
      SET_TO _azure_blob_uploader_storage_account = $(ACCOUNT)
      SET_TO _azure_blob_uploader_key = $(KEY)
      SET_TO _azure_blob_uploader_container = $(CONTAINER)
      SET_TO _azure_blob_uploader_blob_name = $(BLOB_NAME)
      SET_TO _azure_blob_uploader_src_type = $(SRC_TYPE)
      SET_TO _azure_blob_uploader_src_data = $(SRC_DATA)
      SET_TO _pathname = $(_PATHNAME)
    -> AzureBlobStorageConnector
AzureBlobStorageConnector
    ACCOUNT_KEY = @Value(_azure_blob_uploader_key)
    ACCOUNT_NAME = @Value(_azure_blob_uploader_storage_account)
    CREDENTIAL_SOURCE = EMBEDDED
    OPERATION_TYPE = Upload
    PARAMETER_SETUP = _FME_SOURCE_TYPE]File]_FME_SOURCE_FILE]@Value(_azure_blob_uploader_src_data)]_FME_SOURCE_FOLDER]<Unused>]_FME_INCLUDE_SUBFOLDERS]<Unused>]_FME_CONTENTS_ONLY]<Unused>]_FME_DATA_TO_UPLOAD]<Unused>]_FME_AZURE_CONTAINER]@Value(_azure_blob_uploader_container)]_FME_UPLOAD_DESTINATION_PATH]@Value(_azure_blob_uploader_blob_name)]_FME_UPLOAD_ATTR_FILENAME]<Unused>]_FME_HANDLE_EXISTING_FILE]Overwrite]_FME_AZURE_MAX_BLOCK_SIZE]4]_FME_METADATA_GROUP]]_FME_AZURE_CUSTOM_HEADERS]]_FME_SAS_GENERATE]NO]_FME_SAS_PERMISSIONS]<Unused>]_FME_SAS_EXPIRY_TIME]<Unused>]_FME_SAS_IP_RANGE]<Unused>]_FME_SAS_HTTPS]<Unused>]_FME_ATTRIBUTES_TO_ADD]]FME_CONTROLLER_QUERY_FILE]azureblobstorageconnector_deps/Upload.fme
    -> Success (output)
    <REJECTED> -> UUIDGenerator
AzureBlobStorageConnector_2
    ACCOUNT_KEY = @Value(_azure_blob_uploader_key)
    ACCOUNT_NAME = @Value(_azure_blob_uploader_storage_account)
    CREDENTIAL_SOURCE = EMBEDDED
    OPERATION_TYPE = Upload
    PARAMETER_SETUP = _FME_SOURCE_TYPE]File]_FME_SOURCE_FILE]@Value(fileOutput)]_FME_SOURCE_FOLDER]<Unused>]_FME_INCLUDE_SUBFOLDERS]<Unused>]_FME_CONTENTS_ONLY]<Unused>]_FME_DATA_TO_UPLOAD]<Unused>]_FME_AZURE_CONTAINER]@Value(_azure_blob_uploader_container)]_FME_UPLOAD_DESTINATION_PATH]@Value(_azure_blob_uploader_blob_name)]_FME_UPLOAD_ATTR_FILENAME]<Unused>]_FME_HANDLE_EXISTING_FILE]Overwrite]_FME_AZURE_MAX_BLOCK_SIZE]4]_FME_METADATA_GROUP]]_FME_AZURE_CUSTOM_HEADERS]]_FME_SAS_GENERATE]NO]_FME_SAS_PERMISSIONS]<Unused>]_FME_SAS_EXPIRY_TIME]<Unused>]_FME_SAS_IP_RANGE]<Unused>]_FME_SAS_HTTPS]<Unused>]_FME_ATTRIBUTES_TO_ADD]]FME_CONTROLLER_QUERY_FILE]azureblobstorageconnector_deps/Upload.fme
    -> Success (output)
    <REJECTED> -> Fail (output)
Success (output)
AttributeRemover_2
    -> Fail (output)
Fail (output)

Bookmark: If file cannot be uploaded, create a copy with a UUID name and palce it in a temp folder
UUIDGenerator
    UUID_ATTR = _uuid
    -> FileSystemDeleteMoveCopyExist [FileName]
FileSystemDeleteMoveCopyExist
    Action = COPY
    FILEINPUT = @Value(_azure_blob_uploader_src_data)
    FILEOUTPUT = @Value(_pathname)/@Value(_uuid).csv.gz
    Success -> AzureBlobStorageConnector_2

FME custom transformer CleanUpBlob

Parameters:
- AZUREDIMENSIONFILE =
- FILEID =
- NAME =

Input (input)
    -> TestFilter
    -> FeatureHolder
TestFilter
    DEFAULT_VALUE = NoFileInAzure
    TEST_LIST = BOOL_OP,OR,COMPOSITE_TEST,<Unused>,TEST_CLAUSE,"TEST @Value(AzureDimensionFile) ATTRIBUTE_HAS_VALUE """"",DimFileExistsInAzure
    DimFileExistsInAzure -> AzureBlobLister
Note: Can we not be more specific! I need to read the entire container
AzureBlobLister
    ACCOUNT = cwsblobstorage01
    CONTAINER = cwsblob01
    DELIMITER = /
    KEY =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
    PREFIX = Dimensions/@Value(Name)_@Value(FileId)
    RECURSIVE = Yes
    Blob -> FeatureHolder_2
FeatureHolder_2
    -> AzureBlobDeleter
AzureBlobDeleter
    ACCOUNT = cwsblobstorage01
    BLOB_NAME = @Value(Blob.Name)
    CONTAINER = cwsblob01
    KEY =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
    Deleted -> AttributeKeeper
    Fail -> AttributeKeeper
Note: Remove all attributes
AttributeKeeper
    CREATE_BULK_MODE_FEATURES = No
    -> FeatureHolder
FeatureHolder
    -> TestFilter_2
TestFilter_2
    DEFAULT_VALUE = <UNFILTERED>
    TEST_LIST = BOOL_OP,OR,COMPOSITE_TEST,<Unused>,TEST_CLAUSE,"TEST @Value(FileId) ATTRIBUTE_HAS_VALUE """"",FileId ATTRIBUTE_HAS_VALUE
    FileId ATTRIBUTE_HAS_VALUE -> Initiator (output)
Initiator (output)

FME custom transformer MultiAzureUpload

Parameters:
- AZUREDIMENSIONFILE =
- DIMENSIONFILE =
- _PATHNAME =

Input (input)
    -> AzureBlobUploader
Note: Send SourceFile to Microsoft Azure
AzureBlobUploader
    ACCOUNT = cwsblobstorage01
    BLOB_NAME = @Value(AzureDimensionFile)
    CONTAINER = cwsblob01
    KEY =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
    SRC_DATA = @Value(DimensionFile)
    SRC_TYPE = FilePath
    _PATHNAME = @Value(_pathname)
    Success -> Success (output)
    Fail -> Failed (output)
Success (output)
Failed (output)

FME custom transformer AzureBlobLister
Lists all blobs in the given storage container. 
Updated to work with Python 3.4+ since v5
Storage account:
  Provide the storage account. Look for this under the portal.azure.com.
Access key:
Provide the access key for the blob inside Azure. You can find this when you select the storage inside the protal.azure.com website, go to settings and then search for "Access keys".
Use access keys to authenticate your applications when making requests to this Azure storage account. Store your access keys securely - for example, using Azure Key Vault - and don't share them. We recommend regenerating your access keys regularly. You are provided two access keys so that you can maintain connections using one key while regenerating the other. 
Container name:
The storage container name. These are listed directly under the storage account pannel. 
Prefix:
An optional prefix that shall be used to filter results, only blob names starting with prefix will be returned. Leave empty to not use filter. 
Delimiter:
A single BlobPrefix feature will be output as a placeholder for all blobs whose names begin with the same substring up to the appearance of the delimiter character. The delimiter may be a single character or a string. 
One way to think of this is like a file path separator.
Recursive:
Should we list all blobs recursively using delimiter.

Parameters:
- ACCOUNT =
- CONTAINER =
- DELIMITER =
- KEY =
- PREFIX =
- RECURSIVE =

Input (input)
    -> FetchParamsAttributeCreator_2
FetchParamsAttributeCreator_2: AttributeCreator
    ATTR_TABLE:
      SET_TO _azure_blob_lister_storage_account = $(ACCOUNT)
      SET_TO _azure_blob_lister_key = $(KEY)
      SET_TO _azure_blob_lister_container = $(CONTAINER)
      SET_TO _azure_blob_lister_prefix = $(PREFIX)
      SET_TO _azure_blob_lister_delimiter = $(DELIMITER)
      SET_TO _azure_blob_lister_recursive = $(RECURSIVE)
    -> PythonCaller_2
PythonCaller_2
    NEW_ATTRIBUTES = _azure_blob_lister_status _azure_blob_lister_error_message _azure_blob_lister_xml_response _azure_blob_lister_n_prefixes _azure_blob_lister_n_blobs
    PYTHONSOURCE:
      from fmeobjects import FMELogFile, FME_INFORM, FME_WARN, FME_ERROR
      #from cStringIO import StringIO
      from io import StringIO, BytesIO
      from AzureAPI import AzureAPI


      class ListFeatureProcessor(object):
          def __init__(self):
              self.logfile = FMELogFile()
              # Make sure to change if Custom transformer is renamed (not transformer instance name - that's what we're fetching)
              self.xformer_name = FME_MacroValues['AzureBlobLister_WORKSPACE_NAME']
          def info(self, message):
              self.logfile.logMessageString('%s: %s' % (self.xformer_name, message), FME_INFORM)
              #self.logfile.logMessageString('%s: %s' % (self.xformer_name, message), FME_WARN) # while developing for popping out
          def debug(self, message):
              pass #self.logfile.logMessageString('%s (DEBUG): %s' % (self.xformer_name, message), FME_WARN) # while developing for popping out
          def input(self,feature):
              try:
                  account = feature.getAttribute('_azure_blob_lister_storage_account')
                  secret = feature.getAttribute('_azure_blob_lister_key')
                  prefix = feature.getAttribute('_azure_blob_lister_prefix')
                  recursive = str(feature.getAttribute('_azure_blob_lister_recursive')).upper() in ('YES', 'Y', '1', 'TRUE')
                  self.debug('Recursive: {}'.format(recursive))
                  delimiter = feature.getAttribute('_azure_blob_lister_delimiter')
                  azure = AzureAPI(account, secret, self.logfile, logprefix = self.xformer_name, loglevel = FME_INFORM)
                  container = feature.getAttribute('_azure_blob_lister_container')
                  n_prefixes = 0
                  n_blobs = 0
                  for returntype, used_prefix, blobxml in azure.list_blobs(container,prefix=prefix,delimiter=delimiter,recursive=recursive):
                      resultfeature = feature.clone()
                      resultfeature.setAttribute('_azure_blob_lister_prefix', used_prefix)
                      resultfeature.setAttribute('_azure_blob_lister_status', returntype)
                      resultfeature.setAttribute('_azure_blob_lister_xml_response', blobxml)
                      self.pyoutput(resultfeature)
                      if 'BlobPrefix' == returntype:
                          n_prefixes += 1
                      elif 'Blob' == returntype:
                          n_blobs += 1
                  feature.setAttribute('_azure_blob_lister_n_prefixes', n_prefixes)
                  feature.setAttribute('_azure_blob_lister_n_blobs', n_blobs)
                  feature.setAttribute('_azure_blob_lister_status', 'initiator_success')
              except Exception as e:
                  feature.setAttribute('_azure_blob_lister_n_prefixes', n_prefixes)
                  feature.setAttribute('_azure_blob_lister_n_blobs', n_blobs)
                  feature.setAttribute('_azure_blob_lister_status', 'initiator_fail')
                  feature.setAttribute('_azure_blob_lister_error_message', str(e))
                  self.logfile.logException(e, FME_ERROR)
              self.pyoutput(feature)
          def close(self):
              del self.logfile
    PYTHONSYMBOL = ListFeatureProcessor
    -> AttributeFilter_2
AttributeFilter_2
    ATTR_NAME = _azure_blob_lister_status
    ATTR_VALUES = BlobPrefix,Blob,initiator_success,<EMPTY>,<MISSING>,<NULL>,<UNFILTERED>,initiator_fail
    BlobPrefix -> XMLFragmenter_3
    Blob -> XMLFragmenter_2
    initiator_success -> AttributeRemover_6
    <EMPTY> -> AttributeRemover_6
    <MISSING> -> AttributeRemover_6
    <NULL> -> AttributeRemover_6
    <UNFILTERED> -> AttributeRemover_6
    initiator_fail -> AttributeRemover_6
XMLFragmenter_3
    ATTRIBUTE_XML = _azure_blob_lister_xml_response
    EMBEDDED_EXPRESSIONS = BlobPrefix
    FEATURE_TYPES_FORMAT_NAME = XML
    FLATTEN_OPTIONS = <structure separator="." map-empty-elements="yes" matched-prefix="attributes" matched-attributes="yes" cardinality="+{?}" structure-prefix="BlobPrefix." child-position-attribute="" except-expression="" ui-mode="basic" matched-ancestor-attributes=""/>
    MERGE_ATTRS = Yes
    NEW_ATTRIBUTES = BlobPrefix.Name xml_id xml_matched_element xml_parent_child_pos xml_parent_id xml_type
    XML_SOURCE_TYPE = Attribute with XML document
    FRAGMENTS -> AttributeRemover_5
AttributeRemover_5
    REMOVE_ATTRS = _azure_blob_lister_container,xml_fragment,xml_parent_id,_azure_blob_lister_delimiter,_azure_blob_lister_key,_azure_blob_lister_n_prefixes,xml_matched_element,_azure_blob_lister_status,xml_id,xml_parent_child_pos,xml_type,_azure_blob_lister_storage_account,_azure_blob_lister_recursive,_azure_blob_lister_error_message,_azure_blob_lister_xml_response,_azure_blob_lister_n_blobs
    -> BlobPrefix (output)
BlobPrefix (output)
XMLFragmenter_2
    ATTRIBUTE_XML = _azure_blob_lister_xml_response
    EMBEDDED_EXPRESSIONS = Blob
    FEATURE_TYPES_FORMAT_NAME = XML
    FLATTEN_OPTIONS = <structure separator="." map-empty-elements="yes" matched-prefix="attributes" matched-attributes="yes" cardinality="+{?}" structure-prefix="Blob." child-position-attribute="" except-expression="" ui-mode="basic" matched-ancestor-attributes=""/>
    MERGE_ATTRS = Yes
    NEW_ATTRIBUTES = Blob.Name Blob.Properties.BlobType Blob.Properties.Cache-Control Blob.Properties.Content-Disposition Blob.Properties.Content-Encoding Blob.Properties.Content-Language Blob.Properties.Content-Length Blob.Properties.Content-MD5 Blob.Properties.Content-Type Blob.Properties.Etag Blob.Properties.Last-Modified Blob.Properties.LeaseState Blob.Properties.LeaseStatus xml_id xml_matched_element xml_parent_child_pos xml_parent_id xml_type
    XML_SOURCE_TYPE = Attribute with XML document
    FRAGMENTS -> AttributeRemover_3
AttributeRemover_3
    REMOVE_ATTRS = Blob.Properties.Last-Modified,Blob.Properties.Content-Language,_azure_blob_lister_key,Blob.Properties.Etag,Blob.Properties.Content-MD5,_azure_blob_lister_storage_account,xml_id,xml_matched_element,Blob.Properties.Content-Type,Blob.Properties.LeaseStatus,_azure_blob_lister_status,Blob.Properties.LeaseState,_azure_blob_lister_container,xml_parent_id,Blob.Properties.Content-Disposition,xml_type,_azure_blob_lister_recursive,_azure_blob_lister_n_blobs,_azure_blob_lister_xml_response,xml_parent_child_pos,_azure_blob_lister_n_prefixes,xml_fragment,_azure_blob_lister_delimiter,_azure_blob_lister_error_message,Blob.Properties.Content-Encoding
    -> Blob (output)
Blob (output)
AttributeRemover_6
    REMOVE_ATTRS = _azure_blob_lister_container,_azure_blob_lister_delimiter,_azure_blob_lister_key,_azure_blob_lister_storage_account,_azure_blob_lister_recursive,_azure_blob_lister_xml_response
    -> Initiator (output)
Initiator (output)
