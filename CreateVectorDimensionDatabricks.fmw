FME workspace CreateVectorDimensionDatabricks.fmw
Title: Add Azure Blob file towards Microsoft SQL Datawarehouse
Description: Objective
To make the Dimensions files available inside the SQL Datawarehouse engine on Azure.
Usage: Execution
    Executed by Jedi_MasterScript. Information for this script is found inside the CubeManager database using <FileId> as only parameter.
    What does it do
    - Linkes the compressed .csv files from a BLOB environment into an SQL External Table.
    - Creates a dimension table D_... based on this external table. (One to one match)
- Checks if we have duplicated GridNums if so we report this in the database.
- Cleanup temp tables and external table
History: 05/05/2016,Jan Bliki,Initial creation,02/09/2016,Jan Bliki,Fix big on Field Alias should use [...] in order to ovoid errors when spaces are used.,02/09/2016,Jan Bliki,Moved away from using FieldAlias as this changes too often and this would require to generate the dimensions every time.

Parameters:
- DestDataset_MSSQL_JDBC_NONSPATIAL =
- FileId =

Writers:
- MSSQL_JDBC_NONSPATIAL_1: MSSQL_JDBC_NONSPATIAL to $(DestDataset_MSSQL_JDBC_NONSPATIAL)

Note: Link the data-files inside blob towards Azure Databricks / The following steps are executed by generating TSQL and execute this inside Databricks
Creator
    GEOMTYPE = Geometry Object
    NUM = 1
    CREATED -> AttributeCreator_6
Note: Create Table Name / D_<Dimension Name>_<FileId>_<Date>_External / D_<Dimension Name>_<FileId>_<Date>_<GridTypeName> / D_<Dimension Name>_<FileId>_<Date>_<GridTypeName>_Temp
CreateTableNames: AttributeCreator
    ATTR_TABLE:
      SET_TO ExternalTableName = D_@Value(Name)_@Value(FileId)_@Value(FileYear)@Value(FileMonth)@Value(FileDay)_External
      SET_TO DWTableName = D_@Value(Name)_@Value(FileId)_@Value(FileYear)@Value(FileMonth)@Value(FileDay)_@Value(GridTypeName)
      SET_TO DWTableNameTemp = D_@Value(Name)_@Value(FileId)_@Value(FileYear)@Value(FileMonth)@Value(FileDay)_Temp
      SET_TO AreaHaScale = @Evaluate((@Value(GridTypeScale) / 100))
      SET_TO SQLDWTableName = D_@Value(Name)_@Value(FileId)_@Value(FileYear)@Value(FileMonth)@Value(FileDay)_@Value(GridTypeName)
    -> AttributeCreator_2
    -> TestFilter
AttributeCreator_17
    ATTR_TABLE:
      SET_TO TransformerPath = STATUSFLAG_SUCCESS
      SET_TO MessageString = Tell database that we succeeded.
    -> AttributeCreator_16_OUTPUT_-__AttributeCreator_INFO_2
AttributeCreator_27
    ATTR_TABLE:
      SET_TO TransformerPath = STATUSFLAG_SUCCESS\SQLExecutor_3
      SET_TO MessageString = Error: @Value(_reader_error).
        WorkSpace: $(WORKSPACE_NAME)
        Transformer name: SQLExecutor_3
    -> AttributeCreator_27_OUTPUT_-__AttributeCreator_21_OUTPUT_-__AttributeCreator_ERROR
AttributeCreator_14
    ATTR_TABLE:
      SET_TO TransformerPath = OVERLAP_IN_DIMENSION
      SET_TO MessageString = Has duplicates: @Value(has_overlaps)
    -> AttributeCreator_16_OUTPUT_-__AttributeCreator_INFO_2
Inspector [off]
AttributeCreator_13
    ATTR_TABLE:
      SET_TO TransformerPath = FIELDS UPPDATED FOR TSQL STATEMENT
      SET_TO MessageString = Continue
    -> AttributeCreator_16_OUTPUT_-__AttributeCreator_INFO_2
Note: INFO
AttributeCreator_16_OUTPUT_-__AttributeCreator_INFO_2: Junction
    -> AttributeCreator_INFO_2
Note: ERROR
AttributeCreator_27_OUTPUT_-__AttributeCreator_21_OUTPUT_-__AttributeCreator_ERROR: Junction
    -> AttributeCreator_21_OUTPUT_-__AttributeCreator_ERROR
AttributeCreator_2
    ATTR_TABLE:
      SET_TO TransformerPath = COMPILE_FIELDS
      SET_TO MessageString = FieldName should be used at this stage.
        If an Alias is set as 'GridNum' we should change it to that FieldName.
    -> AttributeCreator_8_OUTPUT_-__AttributeCreator_INFO_2
Aggregator_5
    ACCUM_ATTRS_NAME = Drop Incoming Attributes
    AGGREGATE_TYPE = Homogeneous Collection (If Possible)
    GROUP_BY = FileId
    MODE = Geometry - Assemble One Level
    ORDERED = No
    SEP = ,
    AGGREGATE -> AttributeCreator_3
AttributeCreator_3
    ATTR_TABLE:
      SET_TO TransformerPath = Micrososft_SQL_DATA_TYPE
      SET_TO MessageString = Detect what type of data type we going to use for the dimention fields
    -> AttributeCreator_8_OUTPUT_-__AttributeCreator_INFO_2
Note: INFO
AttributeCreator_8_OUTPUT_-__AttributeCreator_INFO_2: Junction
    -> AttributeCreator_INFO_2
AttributeCreator_INFO_2: Junction
    -> AttributeCreator_INFO
AttributeCreator_INFO
    ATTR_TABLE = SET_TO MessageType = INFO
    -> AttributeKeeper_2
AttributeCreator_35
    ATTR_TABLE:
      SET_TO TransformerPath = GetMetaInfo
      SET_TO MessageString = Error: @Value(_reader_error).
        WorkSpace: $(WORKSPACE_NAME)
        Transformer name: GetMetaInfo
    -> AttributeCreator_35_OUTPUT_-__AttributeCreator_21_OUTPUT_-__AttributeCreator_ERROR
AttributeCreator_36
    ATTR_TABLE:
      SET_TO TransformerPath = SQLExecutor
      SET_TO MessageString = Error: @Value(_reader_error).
        WorkSpace: $(WORKSPACE_NAME)
        Transformer name: SQLExecutor
    -> AttributeCreator_35_OUTPUT_-__AttributeCreator_21_OUTPUT_-__AttributeCreator_ERROR
AttributeCreator_35_OUTPUT_-__AttributeCreator_21_OUTPUT_-__AttributeCreator_ERROR: Junction
    -> AttributeCreator_21_OUTPUT_-__AttributeCreator_ERROR
AttributeCreator_21_OUTPUT_-__AttributeCreator_ERROR: Junction
    -> AttributeCreator_ERROR
AttributeCreator_ERROR
    ATTR_TABLE = SET_TO MessageType = ERROR
    -> AttributeKeeper_2
AttributeKeeper_2
    CREATE_BULK_MODE_FEATURES = No
    KEEP_ATTRS = MessageType,TransformerPath,MessageString,FileId
    -> JediLogWritter
JediLogWritter
    FILEID = $(FileId)
    MESSAGESTRING = @Value(MessageString)
    MESSAGETYPE = @Value(MessageType)
    OBJECTPROCESSED = Dimension
    SQLServerConn = CubeManager
    TRANSFORMERPATH = $(WORKSPACE_NAME)\STEP4: AZURE BLOB TO SQL SW\@Value(TransformerPath)
    -> Tester
Tester
    BOOL_OP = OR
    TEST_CLAUSE = TEST @Value(MessageType) = ERROR
    TEST_MODE = TEST
    PASSED -> Terminator_2
Terminator_2 [off]
    MESSAGE = Translation Terminated: @Value(MessageString)
AttributeCreator
    ATTR_TABLE = SET_TO SQLDWTableName = D_VectorFilesTesting_806_202169_100m
    -> JediLogWritter_startjob_8
DeleteDimensionStats
    FILEID = @Value(FileId)
    fields = @Value(fields)
    -> FeatureReader [INITIATOR]

Bookmark: Tell DB we are executing the job
Note: Reset the database and provide the job_id so log information can be found easily.
AttributeCreator_6
    ATTR_TABLE:
      SET_TO _FME_JOB_ID = FME_CONDITIONAL:DEFAULT_VALUE'$(FME_JOB_ID)'BOOL_OP;AND;COMPOSITE_TEST;<Unused>;TEST $(FME_JOB_ID) ATTRIBUTE_IS_MISSING _FME_BLANK_STRING_;TEST $(FME_JOB_ID) NOT_ATTRIBUTE_HAS_VALUE _FME_BLANK_STRING_'-1'FME_NUM_CONDITIONS2___
      SET_TO FileId = $(FileId)
    -> SQLExecutor [INITIATOR]
SQLExecutor
    COMBINE_ATTRS = Result Attributes Only
    COMBINE_GEOM = Initiator Geometry Only
    DATASET = CubeManager
    FORMAT = MSSQL_ADO
    MSSQL_ADO_COMMAND_TIMEOUT = 30
    MSSQL_ADO_CREATE_FEATURE_TABLES_FROM_DATA = Yes
    MSSQL_ADO_NAMED_CONNECTION = CubeManager
    MSSQL_ADO_QUERY_FEATURE_TYPES_FOR_MERGE_FILTERS = Yes
    SQL_STATEMENT:
      UPDATE dbo.Files
          set FMEJobIdSQLDWCreated = @Value(_FME_JOB_ID),
              FMEJobIdSQLDWCreatedStatus=0,
              TotalRecords=0
      WHERE FileId = @Value(FileId)
    INITIATOR -> GetMetaInfo [INITIATOR]
    <REJECTED> -> AttributeCreator_36

Bookmark: Retrieve details from DB
Note: Get info from CubeManager database.
GetMetaInfo: SQLExecutor
    COMBINE_ATTRS = Keep Result Attributes if Conflict
    COMBINE_GEOM = Initiator Geometry Only
    DATASET = CubeManager
    EXPOSED_ATTRIBUTE_LIST = AzureDimensionFile FieldAlias FieldName FieldType FileDay FileMonth FileYear IgnoreField Name SQLDWTableName GridTypeName GridTypeScale ExternalFileFormat TSQL_Userdefined
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = CubeManager
    MSSQL_ADO_QUERY_FEATURE_TYPES_FOR_MERGE_FILTERS = Yes
    SQL_STATEMENT:
      Select
       dbo.[CubeDimensions].[Name] as Name
      , dbo.[Files].[AzureDimensionFile] as AzureDimensionFile
      , dbo.[FIles].[SQLDWTableName] as SQLDWTableName
      , DATEPART(year,dbo.[Files].[SourceFileReceived]) as FileYear
      , DATEPART(month,dbo.[Files].[SourceFileReceived]) as FileMonth
      , DATEPART(day,dbo.[Files].[SourceFileReceived]) as FileDay
      , dbo.[Fields].Alias as FieldAlias
      , dbo.[Fields].FieldName as FieldName
      , dbo.[Fields].FieldType as FieldType
      , dbo.[Fields].IgnoreField as IgnoreField
      , dbo.[GridTypes].name as GridTypeName
      , dbo.[DimensionConverters].FileFormat as ExternalFileFormat
      , dbo.[GridTypes].XCellSpacing as GridTypeScale
      , dbo.[Files].[TSQL] as TSQL_Userdefined
       from dbo.[CubeDimensions]
       inner join dbo.[Files] on dbo.[CubeDimensions].CubeDimensionId = dbo.[Files].CubeDimensionId
       left join dbo.[Fields] on dbo.[Files].FileId = dbo.[Fields].FileId and dbo.[Fields].FieldOrder is not null
      inner join dbo.[GridTypes] on dbo.[GridTypes].[GridTypeId] = dbo.[CubeDimensions].[GridTypeId]
      inner join dbo.[DimensionConverters] on dbo.[DimensionConverters].[Name] = dbo.[CubeDimensions].[FMEConversionProcess]
      where Files.FileId = @Value(FileId)
      order by FieldOrder
    RESULT -> DefineSQLDataType
    <REJECTED> -> AttributeCreator_35

Bookmark: Microsoft SQL DATA TYPE
Note: Detect what type of data type we going to use for the dimention fields / WARNING: We now translate the data type on the dimension processing level towards Microsoft SQL data types. This block is kept for compatibility reasons.
DefineSQLDataType
    FIELDTYPE = @Value(FieldType)
    -> CreateFieldsNames
    -> Aggregator_5

Bookmark: COMPILE FIELDS
Note: FieldName should be used at this stage. / If an Alias is set as 'GridNum' we should change it to that FieldName.
Note: Compile Field definitions / use the Alias for the fields
CreateFieldsNames: AttributeCreator
    ATTR_TABLE:
      SET_TO SQLFieldsDefinition = FME_CONDITIONAL:DEFAULT_VALUE'@ReplaceString(@Value(FieldName)," ","_")   @ReplaceString(@Value(SQLFieldType),"nvarchar","varchar")'BOOL_OP;OR;COMPOSITE_TEST;<Unused>;TEST @Value(FieldAlias) = GridNum'@ReplaceString(@Value(FieldAlias)," ","_")   @ReplaceString(@Value(SQLFieldType),"nvarchar","varchar")'FME_NUM_CONDITIONS2___
      SET_TO SQLFieldsNoGridNum = FME_CONDITIONAL:DEFAULT_VALUE'@ReplaceString(@Value(FieldName)," ","_")'BOOL_OP;OR;COMPOSITE_TEST;<Unused>;TEST @Value(FieldAlias) = GridNum'GridNum'FME_NUM_CONDITIONS2___
    -> Aggregator
Aggregator
    ACCUM_ATTRS_NAME = Drop Incoming Attributes
    CONCAT_ATTRS = SQLFieldsNoGridNum SQLFieldsDefinition
    GROUP_BY = AzureDimensionFile _FME_JOB_ID GridTypeScale Name FileId TSQL_Userdefined FileMonth FileYear GridTypeName ExternalFileFormat FileDay SQLDWTableName
    MODE = Attributes Only
    ORDERED = No
    SEP = ",\n"
    AGGREGATE -> StringConcatenator
Note: Concat GridNUm10Km and AreaHa fileds
StringConcatenator
    ACTION = Overwrite Existing Attributes
    ATTRLIST = SQLFieldsDefinition
    PARM_LINE = fme_basicstring:27%31:@Value(SQLFieldsDefinition),GridNum10Km bigint, AreaHa int
    -> CreateTableNames

Bookmark: TSQL OR BLOB
TestFilter
    DEFAULT_VALUE = TSQL
    TEST_LIST = "BOOL_OP,OR,COMPOSITE_TEST,""""""<Unused>"""""",TEST_CLAUSE,TEST TSQL_Userdefined ATTRIBUTE_VALUE_NULL """,BLOB
    BLOB -> CallProcessCubeJob [DatabrickAPICallerInput]
    TSQL -> CreateDimensionFromTSQL [CreateDImFromTSQL]

Bookmark: CREATE DATABRICKS VECTOR DATASET
CallProcessCubeJob: DatabricksAPICaller
    COMMAND = run-now
    DOMAIN = northeurope.azuredatabricks.net
    JOBID = 13
    METHOD = POST
    PARAMETER = "fields":"@Value(SQLFieldsDefinition)","source_file":"@Value(AzureDimensionFile)","target_table":"@Value(SQLDWTableName)"
    TOKEN =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
    CallDatabricksJob_Output -> testRunJobError
Note: Check if the Job started correctly
testRunJobError: Tester
    BOOL_OP = OR
    COMPOSITE_TEST = 1 OR 2
    TEST_CLAUSE:
      TEST RunId ATTRIBUTE_IS_MISSING ""
      TEST @Value(RunId) = 0
    TEST_MODE = TEST
    PASSED -> AttributeCreator_32
    FAILED -> JobStartTimer
    FAILED -> AttributeCreator_11
AttributeCreator_32
    ATTR_TABLE:
      SET_TO TransformerPath = DatabricksNotepadCaller
      SET_TO MessageString = Error running CreateVectorDataframe job: @Value(error)
      SET_TO _error = Error running CreateVectorDataframe job: @Value(error)
    -> AttributeCreator_27_OUTPUT_-__AttributeCreator_21_OUTPUT_-__AttributeCreator_ERROR
Note: In order to checkhow long it takes tp start the cluster
JobStartTimer: AttributeCreator
    ATTR_TABLE = SET_TO StartTime = @DateTimeNow()
    -> WaitUntilDatabtricksJobCompleted [CheckJobStatus_Input]
Note: Wait until Dtabricks completes or times out to start the cliuster
WaitUntilDatabtricksJobCompleted
    MINUTESTOTIMEOUT = 20
    RUNID = @Value(RunId)
    STARTTIME = @Value(StartTime)
    TestFilter_TERMINATED -> TestJobSuccess
AttributeCreator_11
    ATTR_TABLE:
      SET_TO TransformerPath = DatabricksJobCaller
      SET_TO MessageString = CreateVectorDataframe job started
    -> AttributeCreator_16_OUTPUT_-__AttributeCreator_INFO_2
TestJobSuccess: Tester
    BOOL_OP = OR
    COMPOSITE_TEST = 1
    TEST_CLAUSE = TEST @Value(noError) = 1
    TEST_MODE = TEST
    PASSED -> AttributeCreator_12
    PASSED -> HasOverlaps
    FAILED -> AttributeCreator_29

Bookmark: JEDI TABLE CREATION USING TSQL
CreateDimensionFromTSQL
    FILEID_2 = @Value(FileId)
    SQLDWTABLENAME = @Value(SQLDWTableName)
    TSQL_USERDEFINED = @Value(TSQL_Userdefined)
    _FME_JOB_ID = @Value(_FME_JOB_ID)
    -> ReplaceQuotes
    -> Inspector_2
    -> SQLExecutor_5 [INITIATOR]
    Error -> AttributeCreator_4
SQLExecutor_5
    COMBINE_ATTRS = Result Attributes Only
    COMBINE_GEOM = Initiator Geometry Only
    DATASET = CubeManager
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = CubeManager
    MSSQL_ADO_QUERY_FEATURE_TYPES_FOR_MERGE_FILTERS = Yes
    SQL_STATEMENT:
      UPDATE dbo.Files
      SET
              AzureDimensionFile = 'Dimensions/@Value(SQLDWTableName)'
      WHERE FileId = @Value(FileId)
    INITIATOR -> Inspector
    INITIATOR -> TestJobSuccess
Note: Fields returns single quotes that cannot be parsed. Replace single with double quotes
ReplaceQuotes: PythonCaller
    PYTHONSOURCE:
      import fme
      import fmeobjects
      # Template Function interface:
      # When using this function, make sure its name is set as the value of
      # the 'Class or Function to Process Features' transformer parameter
      def processFeature(feature):
          pass

      # Template Class Interface:
      # When using this class, make sure its name is set as the value of
      # the 'Class or Function to Process Features' transformer parameter
      class FeatureProcessor(object):
          def __init__(self):
              pass
          def input(self,feature):
              fields = feature.getAttribute('fields')
              fields = fields.replace("'col_name': '", '"col_name": "')
              fields = fields.replace("', 'data_type': '",'", "data_type":"')
              fields = fields.replace("'}",'"}')
              feature.setAttribute('fields',fields)

              self.pyoutput(feature)
          def close(self):
              pass
    PYTHONSYMBOL = FeatureProcessor
    -> CreateFieldsForTSQLJob [Initiator]
Inspector_2 [off]
AttributeCreator_4
    ATTR_TABLE:
      SET_TO TransformerPath = DatabrickJobs error
      SET_TO MessageString = Error Running CreateTSQLDimension notebook
        Cmd:@Value(cmd) Error: @Value(error)
        WorkSpace: $(WORKSPACE_NAME)

      SET_TO _error = Error Running CreateTSQLDimension notebook
        Cmd:@Value(cmd) Error: @Value(error)
        WorkSpace: $(WORKSPACE_NAME)
    -> AttributeCreator_27_OUTPUT_-__AttributeCreator_21_OUTPUT_-__AttributeCreator_ERROR

Bookmark: OVERLAP IN DIMENSION
HasOverlaps: Tester
    BOOL_OP = OR
    COMPOSITE_TEST = 1
    TEST_CLAUSE = TEST @Value(has_overlaps) > 0
    TEST_MODE = TEST
    PASSED -> OverlapHash_To_1 [INITIATOR]
    FAILED -> OverlapHash_To_0 [INITIATOR]
Note: If a dimension has overlapping areas. It should be notified in the database.
OverlapHash_To_1: SQLExecutor
    COMBINE_ATTRS = Keep Initiator Attributes if Conflict
    COMBINE_GEOM = Initiator Geometry Only
    DATASET = CubeManager
    FORMAT = MSSQL_ADO
    MSSQL_ADO_COMMAND_TIMEOUT = 30
    MSSQL_ADO_CREATE_FEATURE_TABLES_FROM_DATA = Yes
    MSSQL_ADO_NAMED_CONNECTION = CubeManager
    MSSQL_ADO_QUERY_FEATURE_TYPES_FOR_MERGE_FILTERS = Yes
    SQL_STATEMENT:
      FME_SQL_DELIMITER ;
      --
      -- Inform that dimension has overlap areas.
      --
      UPDATE dbo.CubeDimensions
          set HasOverLap = 1
      WHERE CubeDimensionId in (Select CubeDimensionId from Files where FileId = @Value(FileId) );
      --
      -- Updates the TotalDuplicates-fields inside the Files table
      --
      UPDATE dbo.Files
          set TotalDuplicates = @Value(has_overlaps)
      wHERE FileId = @Value(FileId);
    INITIATOR -> SQLExecutor_3 [INITIATOR]
    INITIATOR -> AttributeCreator_14
    <REJECTED> -> AttributeCreator_15
OverlapHash_To_0: SQLExecutor
    COMBINE_ATTRS = Keep Initiator Attributes if Conflict
    COMBINE_GEOM = Initiator Geometry Only
    DATASET = CubeManager
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = CubeManager
    MSSQL_ADO_QUERY_FEATURE_TYPES_FOR_MERGE_FILTERS = Yes
    SQL_STATEMENT:
      FME_SQL_DELIMITER ;
      --
      -- Reset HasOverLap attribute
      --
      UPDATE dbo.CubeDimensions
          set HasOverLap = 0
      WHERE CubeDimensionId in (Select CubeDimensionId from Files where FileId = @Value(FileId) );

      --
      -- Updates the TotalDuplicates-fields inside the Files table
      --
      UPDATE dbo.Files
          set TotalDuplicates = 0
      wHERE FileId = @Value(FileId);

      -- Remove HasOverlap attribute in case it exists.
      --IF EXISTS(SELECT TOP 1 FieldId
      --  FROM [CubeManager].[dbo].[Fields]
      --  where FileId = @Value(FileId)
      --  and FieldName = 'OverlapHash')
      -- BEGIN
      --	DELETE dbo.Fields
      --	WHERE FileId = @Value(FileId)
      --	and FieldName = 'OverlapHash'
      --  END;
    INITIATOR -> SQLExecutor_3 [INITIATOR]
    INITIATOR -> AttributeCreator_14
    <REJECTED> -> AttributeCreator_15
AttributeCreator_15
    ATTR_TABLE:
      SET_TO TransformerPath = OVERLAP_IN_DIMENSION
      SET_TO MessageString = @Value(_reader_error)
      SET_TO _error = @Value(_reader_error)
    -> AttributeCreator_27_OUTPUT_-__AttributeCreator_21_OUTPUT_-__AttributeCreator_ERROR
AttributeCreator_12
    ATTR_TABLE:
      SET_TO TransformerPath = DataBricksNotepadCaller
      SET_TO MessageString = CREATEVECTORDATAFRAME notebook
        The process was successfull
    -> AttributeCreator_16_OUTPUT_-__AttributeCreator_INFO_2
AttributeCreator_29
    ATTR_TABLE:
      SET_TO TransformerPath = DatabrickJobs error
      SET_TO MessageString = Error Running CREATEVECTORDATAFRAME notebook
        Cmd:@Value(cmd) Error: @Value(error)
        WorkSpace: $(WORKSPACE_NAME)

      SET_TO _error = Error Running CREATELOOKUPDATAFRAME notebook
        Cmd:@Value(cmd) Error: @Value(error)
        WorkSpace: $(WORKSPACE_NAME)
    -> AttributeCreator_27_OUTPUT_-__AttributeCreator_21_OUTPUT_-__AttributeCreator_ERROR

Bookmark: STATUSFLAG SUCCESS
Note: Tell database that we succeeded.
SQLExecutor_3
    COMBINE_ATTRS = Result Attributes Only
    COMBINE_GEOM = Initiator Geometry Only
    DATASET = CubeManager
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = CubeManager
    MSSQL_ADO_QUERY_FEATURE_TYPES_FOR_MERGE_FILTERS = Yes
    SQL_STATEMENT:
      UPDATE dbo.Files
          set ErrorMessages = '',
              FMEJobIdSQLDWCreatedStatus=1,
              SQLDWTableName = '@Value(SQLDWTableName)',
              SQLDWTableNameCreated = getdate(),
              TotalRecords=@Value(num_records)
      WHERE FileId = @Value(FileId)
    INITIATOR -> AttributeCreator_17
    INITIATOR -> SQLExecutor_4 [INITIATOR]
    INITIATOR -> JediLogWritter_startjob_8
    <REJECTED> -> AttributeCreator_27

Bookmark: Update event log and UpdatedDate
SQLExecutor_4
    COMBINE_ATTRS = Result Attributes Only
    COMBINE_GEOM = Initiator Geometry Only
    DATASET = CubeManager
    FORMAT = MSSQL_ADO
    MSSQL_ADO_COMMAND_TIMEOUT = 30
    MSSQL_ADO_CREATE_FEATURE_TABLES_FROM_DATA = Yes
    MSSQL_ADO_NAMED_CONNECTION = CubeManager
    MSSQL_ADO_QUERY_FEATURE_TYPES_FOR_MERGE_FILTERS = Yes
    SQL_STATEMENT:
      	declare @dimId int
      	select @dimId = CubeDimensionId from Files where FileId= @Value(FileId)

      	update CubeDimensions
      	set lastupdated= GetDate() where CubeDimensionId= @dimId

      	insert into EventLog (DateTime,[Username],[EntityType],[EntityId],[FileId],[Operation]  )
      	values (
      		getdate(),
      		'FME',
      		'Dimension',
      		@dimId,
      		@Value(FileId),
      		'Updated')

Bookmark: FIELDS UPPDATED FOR TSQL STATEMENT
CreateFieldsForTSQLJob
    FIELDS = @Value(fields)
    FILEID = @Value(FileId)
    Continue -> AttributeCreator_13

Bookmark: Process statistics
JediLogWritter_startjob_8
    FILEID = $(FileId)
    MESSAGESTRING = Calling RunDatabricksJob CreateStatistocs
    MESSAGETYPE = INFO
    OBJECTPROCESSED = Dimension
    SQLServerConn = CubeManager
    TRANSFORMERPATH = $(WORKSPACE_NAME)\CreateVectorDimensionDatabricks
    -> CallProcessCubeJob_CreateStatistics [DatabrickAPICallerInput]
CallProcessCubeJob_CreateStatistics: DatabricksAPICaller
    COMMAND = run-now
    DOMAIN = northeurope.azuredatabricks.net
    JOBID = 18
    METHOD = POST
    PARAMETER = "EntityName":"jedi_dimensions.@Value(SQLDWTableName)"
    TOKEN =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
    CallDatabricksJob_Output -> testRunJobError_2
Note: Check if the Job started correctly
testRunJobError_2: Tester
    BOOL_OP = OR
    COMPOSITE_TEST = 1 OR 2
    TEST_CLAUSE:
      TEST RunId ATTRIBUTE_IS_MISSING ""
      TEST @Value(RunId) = 0
    TEST_MODE = TEST
    PASSED -> JediLogWritter_startjob_5
    FAILED -> JediLogWritter_startjob_7
JediLogWritter_startjob_5
    FILEID = $(FileId)
    MESSAGESTRING = RunDatabricksJobError: @Value(error)
    MESSAGETYPE = ERROR
    OBJECTPROCESSED = Dimension
    SQLServerConn = CubeManager
    TRANSFORMERPATH = $(WORKSPACE_NAME)\CreateVectorDimensionDatabricks
    -> ErrorRunningJob_2
ErrorRunningJob_2: AttributeCreator
    ATTR_TABLE = SET_TO ErrorString = Error running CreateDataFrame job: @Value(error)
JediLogWritter_startjob_7
    FILEID = $(FileId)
    MESSAGESTRING = RunDatabricksJobStarted
    MESSAGETYPE = INFO
    OBJECTPROCESSED = Dimension
    SQLServerConn = CubeManager
    TRANSFORMERPATH = $(WORKSPACE_NAME)\CreateVectorDimensionDatabricks
    -> JobStartTimer_2
Note: In order to checkhow long it takes tp start the cluster
JobStartTimer_2: AttributeCreator
    ATTR_TABLE = SET_TO StartTime = @DateTimeNow()
    -> WaitUntilDatabtricksJobCompleted_2 [CheckJobStatus_Input]
Note: Wait until Dtabricks completes or times out to start the cliuster
WaitUntilDatabtricksJobCompleted_2
    MINUTESTOTIMEOUT = 20
    RUNID = @Value(RunId)
    STARTTIME = @Value(StartTime)
    TestFilter_TERMINATED -> TestJobSuccess_2
    TestFilter_TERMINATED -> JediLogWritter_startjob_9
TestJobSuccess_2: Tester
    BOOL_OP = OR
    COMPOSITE_TEST = 1
    TEST_CLAUSE = TEST @Value(noError) = 1
    TEST_MODE = TEST
    PASSED -> ReplaceQuotesStatsFields
Note: Fields returns single quotes that cannot be parsed. Replace single with double quotes
ReplaceQuotesStatsFields: PythonCaller
    PYTHONSOURCE:
      import fme
      import fmeobjects
      # Template Function interface:
      # When using this function, make sure its name is set as the value of
      # the 'Class or Function to Process Features' transformer parameter
      def processFeature(feature):
          pass

      # Template Class Interface:
      # When using this class, make sure its name is set as the value of
      # the 'Class or Function to Process Features' transformer parameter
      class FeatureProcessor(object):
          def __init__(self):
              pass
          def input(self,feature):
              fields = feature.getAttribute('fields')
              fields = fields.replace("'fieldname': '", '"fieldname": "')
              fields = fields.replace("', 'grouporder':",'", "grouporder":')
              fields = fields.replace("'fieldValue': '",'"fieldValue": "')
              fields = fields.replace("', 'TotalRecord':",'", "TotalRecord":')
              fields = fields.replace("'fieldValue'",'"fieldValue"')
              fields = fields.replace("'TotalRecord'",'"TotalRecord"')

              feature.setAttribute('fields',fields)
              self.pyoutput(feature)
          def close(self):
              pass
    PYTHONSYMBOL = FeatureProcessor
    -> DeleteDimensionStats [Initiator]
JediLogWritter_startjob_9
    FILEID = $(FileId)
    MESSAGESTRING = Databricks job completed
    MESSAGETYPE = INFO
    OBJECTPROCESSED = Dimension
    SQLServerConn = CubeManager
    TRANSFORMERPATH = $(WORKSPACE_NAME)\CreateVectorDimensionDatabricks

Bookmark: Download and parse JSON from BlobStorage
FeatureReader
    ATTR_ACCUM_MODE = Only Use Result
    COMBINE_GEOM = Use Result
    DATASET = https://cwsblobstorage01.blob.core.windows.net/cwsblob01/statistics/@Value(SQLDWTableName).json
    FORMAT = JSON
    JSON_DECODE_TEXT_STRINGS = Yes
    JSON_FEATURE_TYPE_KEY = json_featuretype
    JSON_FLATTEN_MODE = ALL_LEVELS
    JSON_GEOMETRY_FORMAT = None
    JSON_SAVE_FRAGMENTS = NO
    JSON_SCAN_MODE = AUTO
    JSON_USE_BASENAME_AS_DEFAULT_FEATURE_TYPE = No
    JSON_USE_SEARCH_ENVELOPE = NO
    OUTPUT_FEATURES_DISPLAY = Schema and Data Features
    <OTHER> -> AttributeExposer
    INITIATOR -> AttributeCreator_5
    <REJECTED> -> JediLogWritter_startjob_15
AttributeExposer
    ATTR_LIST = fieldname,fieldValue,grouporder,TotalRecord
    -> AttributeCreator_7
AttributeCreator_7
    ATTR_TABLE:
      SET_TO FieldName = @Value(fieldname)
      SET_TO FieldValue = @Value(fieldValue)
      SET_TO GroupOrder = @Value(grouporder)
      SET_TO TotalRecords = @Value(TotalRecord)
    -> AttributeKeeper_6
AttributeKeeper_6
    CREATE_BULK_MODE_FEATURES = NO
    KEEP_ATTRS = FieldName,FieldValue,GroupOrder,TotalRecords,FileId
    -> ParameterFetcher

Bookmark: Field Statistcis
ParameterFetcher
    ATTR_LIST = FileId $(FileId)
    -> FieldStatistics (writer MSSQL_JDBC_NONSPATIAL_1)
FieldStatistics (writer MSSQL_JDBC_NONSPATIAL_1)
    attributes: FileId integer, FieldName varchar(50), FieldValue varchar(500), TotalRecords integer, GroupOrder integer
JediLogWritter_startjob_15
    FILEID = $(FileId)
    MESSAGESTRING = JSON with stats doesn't exist
    MESSAGETYPE = WARNING
    OBJECTPROCESSED = Cube
    SQLServerConn = CubeManager
    TRANSFORMERPATH = $(WORKSPACE_NAME)\CreateDatabricksDimension

Bookmark: Delete JSON from BlobStorage once read
AttributeCreator_5
    ATTR_TABLE = SET_TO JSONPathInBlobStorage = statistics/@Value(SQLDWTableName).json
    -> AzureBlobStorageConnector
AzureBlobStorageConnector
    CREDENTIAL_SOURCE = WEBCONN
    OPERATION_TYPE = Delete
    PARAMETER_SETUP = _FME_AZURE_CONTAINER]cwsblob01]_FME_FILEID]@Value(JSONPathInBlobStorage)]FME_CONTROLLER_QUERY_FILE]azureblobstorageconnector_deps/Delete.fme
    _FME_AZURE_CONNECTION = JEDI Azure Storage

FME custom transformer CreateDimensionFromTSQL

Parameters:
- FILEID_2 =
- SQLDWTABLENAME =
- TSQL_USERDEFINED =
- _FME_JOB_ID =

Note: Send SourceFile to Microsoft Azure
CreateDImFromTSQL (input)
    -> Production_or_Development
Output (output)
Error (output)

Bookmark: Build a text file with TSQL to avoid parameter max length condition
Production_or_Development: TestFilter
    DEFAULT_VALUE = DEVELOPMENT
    TEST_LIST = "BOOL_OP,OR,COMPOSITE_TEST,""""""1"""""",TEST_CLAUSE,TEST @Value(_FME_JOB_ID) != -1",PRODUCTION
    PRODUCTION -> CreateTSQLFilePath
    DEVELOPMENT -> CreateTSQLFilePathDebug
Note: Create temp folder to generate the json file
CreateTSQLFilePath: TempPathnameCreator
    EXTENSION = sql
    PATHNAME_ATTR = tsqlFile
    -> RemoveTabsAndNewLines
CreateTSQLFilePathDebug: AttributeCreator
    ATTR_TABLE = SET_TO tsqlFile = S:\Common workspace\CrossProjects\Jedi\Bilbomatica\Oskar\Temp\tsgl.sql
    -> RemoveTabsAndNewLines
RemoveTabsAndNewLines: StringReplacer
    CASE = NO
    FIND_TEXT = \n|\t|\s{2,}
    NO_MATCH = _FME_NO_OP_
    REGEXP = YES
    REPLACE_TEXT = " "
    SRC_ATTRS = TSQL_Userdefined
    -> AttributeCreator
AttributeCreator
    ATTR_TABLE = SET_TO text_line_data = @Value(TSQL_Userdefined)
    -> FeatureWriter [text_line]
FeatureWriter
    DATASET = @Value(tsqlFile)
    DATASET_ATTR = _dataset
    FEATURE_TYPE_LIST_ATTR = _feature_type
    FORMAT = TEXTLINE
    MORE_SUMMARY_ATTRS = SQLDWTableName tsqlFile FileId
    TEXTLINE_COORDINATE_SYSTEM_GRANULARITY = FEATURE
    TEXTLINE_DESTINATION_DATASETTYPE_VALIDATION = Yes
    TEXTLINE_ENCODING = UTF-8
    TEXTLINE_END_OF_LINE = System
    TEXTLINE_MIME_TYPE = text/plain
    TEXTLINE_OVERWRITE_FILE = YES
    TEXTLINE_WRITE_LAST_EOL = YES
    TEXTLINE_WRITE_UTF8_BOM = YES
    TOTAL_FEATURES_WRITTEN_ATTR = _total_features_written
    SUMMARY -> CubeTableNamesAttributeKeeper
CubeTableNamesAttributeKeeper: AttributeCreator
    ATTR_TABLE:
      SET_TO destFile = CubeSourceDataFile/@UUID().sql
      SET_TO FileId = @Value(_feature_type{0}.FileId)
      SET_TO SQLDWTableName = @Value(_feature_type{0}.SQLDWTableName)
    -> JediLogWritter_startjob_4

Bookmark: Send TSQL file to Azure
JediLogWritter_startjob_4
    FILEID = @Value(FileId)
    MESSAGESTRING = Upload TSQL file to Azure
    MESSAGETYPE = INFO
    OBJECTPROCESSED = Dimension
    SQLServerConn = CubeManager
    TRANSFORMERPATH = $(WORKSPACE_NAME)\CreateVectorDimensionDatabricks
    -> AzureBlobUploader
Note: Send SourceFile to Microsoft Azure
AzureBlobUploader
    ACCOUNT = cwsblobstorage01
    BLOB_NAME = @Value(destFile)
    CONTAINER = cwsblob01
    KEY =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
    SRC_DATA = @Value(_dataset)
    SRC_TYPE = FilePath
    Success -> JediLogWritter_startjob_2
JediLogWritter_startjob_2
    FILEID = @Value(FileId)
    MESSAGESTRING = Calling RunDatabricksJob
    MESSAGETYPE = INFO
    OBJECTPROCESSED = Dimension
    SQLServerConn = CubeManager
    TRANSFORMERPATH = $(WORKSPACE_NAME)\CreateCubeByViewAndTableDatabricks
    -> CallProcessDimensionFromTSQL [DatabrickAPICallerInput]

Bookmark: Call CreateTSQLDimension databricks notebook
CallProcessDimensionFromTSQL: DatabricksAPICaller
    COMMAND = run-now
    DOMAIN = northeurope.azuredatabricks.net
    JOBID = 21
    METHOD = POST
    PARAMETER = "SQLFile":"@Value(destFile)","TargetDimension":"@Value(SQLDWTableName)"
    TOKEN =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
    CallDatabricksJob_Output -> testRunJobError
Note: Check if the Job started correctly
testRunJobError: Tester
    BOOL_OP = OR
    COMPOSITE_TEST = 1 OR 2
    TEST_CLAUSE:
      TEST RunId ATTRIBUTE_IS_MISSING ""
      TEST @Value(RunId) = 0
    TEST_MODE = TEST
    PASSED -> AttributeCreator_32
    FAILED -> JobStartTimer
AttributeCreator_32
    ATTR_TABLE:
      SET_TO TransformerPath = DatabricksNotepadCaller
      SET_TO MessageString = Error running CreateVectorDataframe job: @Value(error)
      SET_TO _error = Error running CreateVectorDataframe job: @Value(error)
Note: In order to checkhow long it takes tp start the cluster
JobStartTimer: AttributeCreator
    ATTR_TABLE = SET_TO StartTime = @DateTimeNow()
    -> WaitUntilDatabtricksJobCompleted [CheckJobStatus_Input]
Note: Wait until Dtabricks completes or times out to start the cliuster
WaitUntilDatabtricksJobCompleted
    MINUTESTOTIMEOUT = 20
    RUNID = @Value(RunId)
    STARTTIME = @Value(StartTime)
    TestFilter_TERMINATED -> TestJobSuccess
TestJobSuccess: Tester
    BOOL_OP = OR
    COMPOSITE_TEST = 1
    TEST_CLAUSE = TEST @Value(noError) = 1
    TEST_MODE = TEST
    PASSED -> Output (output)
    FAILED -> Error (output)

FME custom transformer WaitUntilDatabtricksJobCompleted

Parameters:
- MINUTESTOTIMEOUT =
- RUNID =
- STARTTIME =

CheckJobStatus_Input (input)
    -> CheckRunStatus [DatabrickAPICallerInput]
CheckRunStatus: DatabricksAPICaller
    COMMAND = runs/get-output
    DOMAIN = northeurope.azuredatabricks.net
    METHOD = GET
    RUNID = @Value(RunId)
    TOKEN =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
    CallDatabricksJob_Output -> CurrentTimer
CurrentTimer: AttributeCreator
    ATTR_TABLE = SET_TO CurrentTime = @DateTimeNow()
    -> TestJobStatus
TestJobStatus: TestFilter
    DEFAULT_VALUE = <UNFILTERED>
    TEST_LIST = "BOOL_OP,OR,COMPOSITE_TEST,""""""1"""""",TEST_CLAUSE,TEST @Value(status) = TERMINATED",TERMINATED,"BOOL_OP,OR,COMPOSITE_TEST,""""""1"""""",TEST_CLAUSE,TEST @Value(status) = PENDING",PENDING,"BOOL_OP,OR,COMPOSITE_TEST,""""""1"""""",TEST_CLAUSE,TEST @Value(status) = RUNNING",RUNNING,"BOOL_OP,OR,COMPOSITE_TEST,""""""1"""""",TEST_CLAUSE,TEST @Value(status) = TERMINATING",TERMINATING
    TERMINATED -> TestFilter_TERMINATED (output)
    PENDING -> TimeOutStartingCluster
    RUNNING -> Decelerator
    TERMINATING -> Decelerator
    <UNFILTERED> -> Decelerator
TimeOutStartingCluster: Tester
    BOOL_OP = OR
    COMPOSITE_TEST = 1
    TEST_CLAUSE = TEST @Value(CurrentTime) >= @DateTimeAdd(@Value(StartTime), @DateTimeIntervalCreate(0,0,0,0,@Value(MinutesToTimeout),0) )
    TEST_MODE = TEST
    PASSED -> CancelRun [DatabrickAPICallerInput]
    FAILED -> Decelerator
CancelRun: DatabricksAPICaller
    COMMAND = runs/cancel
    DOMAIN = northeurope.azuredatabricks.net
    METHOD = POST
    RUNID = @Value(RunId)
    TOKEN =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
    CallDatabricksJob_Output -> SetErrorInDatabricksResult
SetErrorInDatabricksResult: AttributeCreator
    ATTR_TABLE:
      SET_TO error = Timeout starting cluster
      SET_TO noError = 0
      SET_TO num_records = 0
      SET_TO has_overlaps = 0
      SET_TO cmd = 0
    -> TestFilter_TERMINATED (output)
TestFilter_TERMINATED (output)
Decelerator
    DECEL_TYPE = Per Feature Delay
    DELAY = 15
    -> CheckJobStatus_Input (output)
CheckJobStatus_Input (output)

FME custom transformer DatabricksAPICaller
Custom Transformer to call Databricks API

Parameters:
- COMMAND =
- DOMAIN =
- JOBID =
- METHOD =
- PARAMETER =
- RUNID =
- TOKEN =

DatabrickAPICallerInput (input)
    -> ParameterFetcher
ParameterFetcher
    ATTR_LIST = _TOKEN $(TOKEN) _DOMAIN $(DOMAIN)
    -> CallDatabricksJob
Note: Call databricks API
CallDatabricksJob: PythonCaller
    NEW_ATTRIBUTES = RunId status result num_records has_overlaps error noError cmd fields
    PYTHONSOURCE:
      import fme
      import fmeobjects
      import json
      import base64
      import requests
      import re


      # Template Function interface:
      # When using this function, make sure its name is set as the value of
      # the 'Class or Function to Process Features' transformer parameter
      def dbfs_rpc(action, body,TOKEN,BASE_URL):
        """ A helper function to make the API request, request/response is encoded/decoded as JSON """
        response = requests.post(
          BASE_URL + action,
          headers={"Authorization":"Bearer " +str(TOKEN) },
          json=body
        )
        return response.json()

      def dbfs_get_rpc(action, body,TOKEN,BASE_URL):
        """ A helper function to make the API request, request/response is encoded/decoded as JSON """
        response = requests.get(
          BASE_URL + action,
          headers={"Authorization":"Bearer " + str(TOKEN) },
          params= body
        )
        return response.json()



      def processFeature(feature):
          pass

      # Template Class Interface:
      # When using this class, make sure its name is set as the value of
      # the 'Class or Function to Process Features' transformer parameter
      class FeatureProcessor(object):
          def __init__(self):
              pass
          def input(self,feature):
              runId= 0
              status=""
              result=""
              num_records =0
              has_overlaps =0
              error= ""
              noError=0
              cmd =0
              fields=""
              try:

                  raw_data = {}
                  if feature.getAttribute('RunId'):
                      raw_data['run_id']= str(feature.getAttribute('RunId'))
                  if feature.getAttribute('JobId'):
                      raw_data['job_id']= feature.getAttribute('JobId')

                  if feature.getAttribute('Parameter'):
                      paramTxt = "{" + str(feature.getAttribute('Parameter')) + "}"
                      formatedParam = paramTxt.replace("\n"," ").replace("\t", " ").replace("  "," ")
                      parameter = json.loads(formatedParam)
                      raw_data['notebook_params'] = parameter

                  DOMAIN = str(feature.getAttribute('_DOMAIN'))
                  TOKEN = str(feature.getAttribute('_TOKEN'))
                  BASE_URL = 'https://%s/api/2.0/jobs/' % (DOMAIN)


                  if feature.getAttribute('Method') == 'POST':
                      handle = dbfs_rpc(feature.getAttribute('Command'), raw_data,TOKEN, BASE_URL)
                  else:
                      handle = dbfs_get_rpc(feature.getAttribute('Command'), raw_data,TOKEN, BASE_URL)
                  noError=0

                  if ('run_id' in handle):
                      runId= handle['run_id']
                  else:
                      runId= str(feature.getAttribute('RunId'))

                  if 'metadata' in handle:
                      if 'state' in handle['metadata']:
                          if 'life_cycle_state' in handle['metadata']['state']:
                              status = handle['metadata']['state']['life_cycle_state']
                          if 'result_state' in handle['metadata']['state']:
                              result = handle['metadata']['state']['result_state']

                      if status == 'TERMINATED' : # and 'notebook_output' in handle:
                          if 'result' in  handle['notebook_output']:
                              output = handle['notebook_output']['result'].replace('\n', ' ').replace('\r', '').replace('\t', '').replace("  ","")
                              res = json.loads(output)
                              noError = res['status']
                              cmd = res['cmd']
                              error = res['error']
                              if 'num_records' in res:
                                  num_records = res['num_records']
                              if 'has_overlaps' in res:
                                  has_overlaps = res['has_overlaps']
                              if 'fields' in res:
                                  fields = str(res['fields'])

              except Exception as err:
                  print("DATABRICKS ERRROR")
                  print("error:" + str(err))
                  feature.setAttribute("RunId",0)
                  feature.setAttribute("error",str(err))
                  feature.setAttribute("noError",0)

              feature.setAttribute("RunId",runId)
              feature.setAttribute("status",status)
              feature.setAttribute("result",result)
              feature.setAttribute("num_records",num_records)
              feature.setAttribute("has_overlaps",has_overlaps)
              feature.setAttribute("error",error)
              feature.setAttribute("noError",noError)
              feature.setAttribute("cmd",cmd)
              feature.setAttribute("fields",fields)
              self.pyoutput(feature)

          def close(self):
              pass
    PYTHONSYMBOL = FeatureProcessor
    -> CallDatabricksJob_Output (output)
CallDatabricksJob_Output (output)

FME custom transformer DeleteDimensionStats

Parameters:
- FILEID =
- fields =

Initiator (input)
    -> Counter
    -> DatabaseDeleter
DatabaseDeleter
    CONDITION = WHERE Clause
    DATASET = CubeManager
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = CubeManager
    MSSQL_ADO_QUERY_FEATURE_TYPES_FOR_MERGE_FILTERS = Yes
    TABLE = dbo.FieldStatistics
    WHERE_CLAUSE = FileId = @Value(FileId)
Iterator (input)
    -> Counter
Counter
    CNT_ATTR = _count
    DOMAIN = counter
    SCOPE = Global
    START = 1
    -> FeatureHolder
FeatureHolder
    -> SQLExecutor [INITIATOR]
SQLExecutor
    COMBINE_ATTRS = Result Attributes Only
    COMBINE_GEOM = Initiator Geometry Only
    DATASET = CubeManager
    EXPOSED_ATTRIBUTE_LIST = FileId NumFields
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = CubeManager
    MSSQL_ADO_QUERY_FEATURE_TYPES_FOR_MERGE_FILTERS = Yes
    SQL_STATEMENT:
      select fileid, count(FieldStatisticsId)
      from [dbo].[FieldStatistics]
      where fileid = @Value(FileId)
      Group BY
      	fileid
    RESULT -> ParameterFetcher_2
    INITIATOR -> Tester
ParameterFetcher_2
    ATTR_LIST = fields $(fields)
    -> TestFilter
TestFilter
    DEFAULT_VALUE = NoFields
    TEST_LIST = "BOOL_OP,OR,COMPOSITE_TEST,""""""1"""""",TEST_CLAUSE,TEST @Value(NumFields) > 0",Fields
    Fields -> Decelerator
    NoFields -> Output (output)
Decelerator
    DECEL_TYPE = Per Feature Delay
    DELAY = 15
    -> Iterator (output)
Iterator (output)
Tester
    BOOL_OP = AND
    COMPOSITE_TEST = 1 AND 2
    TEST_CLAUSE:
      TEST @Value(_count) = 1
      TEST @Value(_matched_records) = 0
    TEST_MODE = TEST
    PASSED -> Output (output)
Output (output)

FME custom transformer SQLDosExecuter
Execute T.SQL statements to Microsoft (Azure) SQL Server and datawarehouse database using the SQLCMD.EXE command. Without revealing user names and passoword and without the SQLExecuter transaction limitation.
Can execute SQL Datawarehouse scripts and report messages and errors back. The current SQLExecuter can't handle a connection to the SQL datawarehouse without a transaction and this creates a problem for some of the commands we need to send. 
Be aware that this transformer has a dependency on the SQLCMD.EXE that needs to be installed on your desktop or FME server. You can find this from the Microsoft website.

Parameters:
- AUTHType =
- Database =
- Password =
- SQL-Statement =
- Server =
- User =

Input (input)
    -> DateTimeStamper
Note: Remember when we started
DateTimeStamper
    DATETIME_ATTR = __TimeSQLstart
    INCLUDE_OFFSET = NO
    STAMP_TYPE = time
    TIMEZONE = local
    -> AttributeCreator_5
AttributeCreator_5
    ATTR_TABLE:
      SET_TO _database = $(Database)
      SET_TO _server = $(Server)
      SET_TO _password = $(Password)
      SET_TO _user = $(User)
      SET_TO T-SQL = $(SQL-Statement)
      SET_TO _authentication = $(AUTHType)
    -> TestFilter_2
Note: Evaluate if we have a TSQL to execute
TestFilter_2
    DEFAULT_VALUE = NO TSQL
    TEST_LIST = BOOL_OP,OR,COMPOSITE_TEST,<Unused>,TEST_CLAUSE,"TEST @Value(T-SQL) ATTRIBUTE_HAS_VALUE """"",TSQL EXIST
    TSQL EXIST -> AttributeCreator
    NO TSQL -> DateTimeStamper_2
AttributeCreator
    ATTR_TABLE:
      SET_TO T-SQL = @Value(T-SQL)
        GO
        EXIT
    -> StringReplacer
StringReplacer
    CASE = NO
    FIND_TEXT = GO\n{0,}GO
    NO_MATCH = _FME_NO_OP_
    REGEXP = YES
    REPLACE_TEXT = "GO\n"
    SRC_ATTRS = T-SQL
    -> PythonCaller_5
Note: When did we finish
DateTimeStamper_2
    DATETIME_ATTR = __TimeSQLend
    INCLUDE_OFFSET = NO
    STAMP_TYPE = time
    TIMEZONE = local
    -> ExpressionEvaluator
Note: Calculate difference
ExpressionEvaluator
    ACTION = Create New Attribute
    EXPRESSION = @Value(__TimeSQLend)-@Value(__TimeSQLstart)
    VAL_ATTR = SQLExecutionTime
    -> AttributeCreator_3
Note: Convert in H:M:S
AttributeCreator_3
    ATTR_TABLE = SET_TO SQLExecutionTime =  @Evaluate(@floor(@Value(SQLExecutionTime)/(60*60))):@Evaluate(@floor( (@Value(SQLExecutionTime)-(@floor(@Value(SQLExecutionTime)/(60*60))*60*60) )/60)):@Evaluate(@floor(@Value(SQLExecutionTime)-(@floor(@Value(SQLExecutionTime)/60)*60)))
    -> PythonCaller_3
Note: Show time in log
PythonCaller_3
    PYTHONSOURCE:
      import fmeobjects
      import locale
      import os
      import subprocess

      class FeatureProcessor(object):
          def __init__(self):
              self.session = fmeobjects.FMESession()
              self.logger = fmeobjects.FMELogFile()
              self.logger_encoding = locale.getdefaultlocale()[1]
              self.pargs_encoding = self.logger_encoding
              self.penv_encoding = self.logger_encoding
              self.pstdio_encoding = self.logger_encoding
              self.xformername = FME_MacroValues.get('SQLDosExecuter_WORKSPACE_NAME')

          def info(self, msg):
              if isinstance(msg, str):
                  msg = u'{}: {}'.format(self.xformername, msg).encode(self.logger_encoding)
              else:
                  msg = '{}: {}'.format(self.xformername, msg)
              self.logger.logMessageString(msg, fmeobjects.FME_INFORM)

          def input(self,feature):
              SQLExecutionTime = feature.getAttribute("SQLExecutionTime")
              systemcall_output = feature.getAttribute("systemcall_output")
              self.info(u'sqlcmd.exe - finnished in {}'.format(SQLExecutionTime))
              self.info(u'-----------------------------------------------------------')
              self.info(u'{}'.format(systemcall_output))

              self.pyoutput(feature)

          def close(self):
              del self.session
              del self.logger
    PYTHONSYMBOL = FeatureProcessor
    -> Success (output)
Success (output)
Note: Show error information
PythonCaller_4
    PYTHONSOURCE:
      import fmeobjects
      import locale
      import os
      import subprocess

      class FeatureProcessor(object):
          def __init__(self):
              self.session = fmeobjects.FMESession()
              self.logger = fmeobjects.FMELogFile()
              self.logger_encoding = locale.getdefaultlocale()[1]
              self.pargs_encoding = self.logger_encoding
              self.penv_encoding = self.logger_encoding
              self.pstdio_encoding = self.logger_encoding
              self.xformername = FME_MacroValues.get('SQLDosExecuter_WORKSPACE_NAME')

          def info(self, msg):
              if isinstance(msg, str):
                  msg = u'{}: {}'.format(self.xformername, msg).encode(self.logger_encoding)
              else:
                  msg = '{}: {}'.format(self.xformername, msg)
              self.logger.logMessageString(msg, fmeobjects.FME_INFORM)
          def error(self, msg):
              if isinstance(msg, str):
                  msg = u'{}: {}'.format(self.xformername, msg).encode(self.logger_encoding)
              else:
                  msg = '{}: {}'.format(self.xformername, msg)
              self.logger.logMessageString(msg, fmeobjects.FME_ERROR)
          def input(self,feature):
              #SQLExecutionTime = feature.getAttribute("SQLExecutionTime")
              systemcall_output = feature.getAttribute("systemcall_output")
              error = feature.getAttribute("_error")
              #self.info(u'sqlcmd.exe - finnished in {}'.format(SQLExecutionTime))
              self.info(u'-------------------------ERROR----------------------------')
              self.error(u'{}'.format(error))
              self.error(u'{}'.format(systemcall_output))
              self.info(u'-------------------------ERROR----------------------------')

              self.pyoutput(feature)

          def close(self):
              del self.session
              del self.logger
    PYTHONSYMBOL = FeatureProcessor
    -> Failed (output)
Failed (output)

Bookmark: USE PYTHON TO HIDE LOGIN/PASSWORD From log
PythonCaller_5
    NEW_ATTRIBUTES = __returncode __stderr __stdout
    PYTHONSOURCE:
      import fmeobjects
      import locale
      import os
      import sys
      import subprocess

      class FeatureProcessor(object):
          def __init__(self):
              self.session = fmeobjects.FMESession()
              self.logger = fmeobjects.FMELogFile()
              self.logger_encoding = locale.getdefaultlocale()[1]
              self.pargs_encoding = self.logger_encoding
              self.penv_encoding = self.logger_encoding
              self.pstdio_encoding = self.logger_encoding
              self.xformername = FME_MacroValues.get('SQLDosExecuter_WORKSPACE_NAME')

          def info(self, msg):
              if isinstance(msg, str):
                  msg = u'{}: {}'.format(self.xformername, msg).encode(self.logger_encoding)
              else:
                  msg = '{}: {}'.format(self.xformername, msg)
              self.logger.logMessageString(msg, fmeobjects.FME_INFORM)

          def parse_param(self, param_name):
              macro_key = '{}_{}'.format(self.xformername, param_name)
              macro_val = FME_MacroValues.get(macro_key, '')
              return self.session.decodeFromFMEParsableText(macro_val)

          def input(self,feature):
              executable = u'sqlcmd'
              args = [executable
                      , u'-S', feature.getAttribute('_server')
                      , u'-d', feature.getAttribute('_database')
                      #, u'-I' # (enable quoted identifiers)
                      , u'-b' # (terminate batch job if there is an error)
                      #, u'-E' # Trusted connection
                     ]
              sql_statements = feature.getAttribute('T-SQL')
              feature.removeAttribute('T-SQL')

              self.info(u'sqlcmd.exe - executes the following T-SQL statement:\n{}'.format(sql_statements))
              self.info(u'on server:' + feature.getAttribute('_server') + ' Database:'+ feature.getAttribute('_database') )
              # Change working directory to the temp folder
              os.chdir(os.environ['TEMP'])
              # Get all Environment varaibles.
              env = os.environ.copy()

              sql_authentication = feature.getAttribute('_authentication')
              feature.removeAttribute('_authentication')
              # If the user asked for an SQL Authentication we then DOS Variables will be added to the temporary shell.
              if sql_authentication == 'SQL Server Authentication':
                  env.update({
                                'SQLCMDUSER': feature.getAttribute('_user')  #.encode(self.penv_encoding)
                              , 'SQLCMDPASSWORD': feature.getAttribute('_password') #.encode(self.penv_encoding)
                             })
              #print(env)
              # Remove all other attributes
              feature.removeAttribute('_user')
              feature.removeAttribute('_password')
              feature.removeAttribute('_database')
              feature.removeAttribute('_server')
              # Execute sub process
              p = subprocess.Popen(args, stdin=subprocess.PIPE, stdout=subprocess.PIPE, stderr=subprocess.PIPE, env=env,shell=True)
              del env
              p.stdin.write(sql_statements.encode(self.pstdio_encoding))
              stdout, stderr = p.communicate()
              feature.setAttribute('__returncode', p.returncode)
              feature.setAttribute('__stdout', stdout.strip().decode(self.pstdio_encoding))
              feature.setAttribute('__stderr', stderr.strip().decode(self.pstdio_encoding))
              self.pyoutput(feature)
          def close(self):
              del self.session
              del self.logger
    PYTHONSYMBOL = FeatureProcessor
    -> AttributeFilter
AttributeFilter
    ATTR_NAME = __returncode
    ATTR_VALUES = 0,<Empty>,<Missing>,<Null>,<Unfiltered>
    0 -> AttributeRemover
    <EMPTY> -> AttributeRenamer_2
    <MISSING> -> AttributeRenamer_2
    <NULL> -> AttributeRenamer_2
    <UNFILTERED> -> AttributeRenamer_2
AttributeRemover
    REMOVE_ATTRS = __stderr
    -> AttributeRenamer
AttributeRenamer
    ATTR_TABLE:
      RENAME_SET_DEFAULT __stdout > systemcall_output
      RENAME_SET_DEFAULT __returncode > systemcall_status
    -> DateTimeStamper_2
AttributeRenamer_2
    ATTR_TABLE:
      RENAME_SET_DEFAULT __stdout > systemcall_output
      RENAME_SET_DEFAULT __returncode > systemcall_status
      RENAME_SET_DEFAULT __stderr > _error
    -> PythonCaller_4

FME custom transformer DefineSQLDataType

Parameters:
- FIELDTYPE =

Input (input)
    -> TestFilter
Note: How is the dimention configured? / For compatibility reasons we still translate the / fme_types but we slowly move towards microsoft sql types
TestFilter
    DEFAULT_VALUE = microsoft sql types
    TEST_LIST = BOOL_OP,OR,COMPOSITE_TEST,<Unused>,TEST_CLAUSE,"TEST @Value(FieldType) BEGINS_WITH fme_",fme types
    fme types -> StringSearcher
    microsoft sql types -> AttributeCreator_4
Note: If it doesn't start with "fme_" then / we assume that this is an Microsoft SQL Data type.
AttributeCreator_4
    ATTR_TABLE = SET_TO SQLFieldType = @Value(FieldType)
    -> StringReplacer
Note: Change numeric to double
StringReplacer
    CASE = NO
    FIND_TEXT = numeric.*
    NO_MATCH = _FME_NO_OP_
    REGEXP = YES
    REPLACE_TEXT = double
    SRC_ATTRS = SQLFieldType,FieldType
    -> StringReplacer_2
Note: Replace float* to float
StringReplacer_2
    CASE = NO
    FIND_TEXT = float.*
    NO_MATCH = _FME_NO_OP_
    REGEXP = YES
    REPLACE_TEXT = float
    SRC_ATTRS = FieldType,SQLFieldType
    -> Output (output)
Output (output)

Bookmark: Split FieltType from Details
Note: Some fieldtypes define length or precision. We capture these so we can pass on the same ínformation to SQL Server
StringSearcher
    CASE = no
    MATCHED_PARTS_ATTR = _TypeParts
    MATCHED_RESULT_ATTR = _first_match
    REGEXP = (fme_char|fme_varchar|fme_decimal)(\(\d{1,}\)|\(\d{1,},\d{1,}\))
    STRING_TO_SEARCH = @Value(FieldType)
    MATCHED -> AttributeCreator
    NOT_MATCHED -> AttributeCreator_2
AttributeCreator
    ATTR_TABLE:
      SET_TO FieldType = @Value(_TypeParts{0}.part)
      SET_TO _FieldTypeDetails = @Value(_TypeParts{1}.part)
    -> AttributeValueMapper
AttributeValueMapper
    DIRECTION = Forward (Source To Destination)
    LUT = fme_char,nvarchar,fme_varchar,nvarchar,fme_decimal,numeric
    SRC = FieldType
    VAL_ATTR = SQLFieldType
    -> AttributeCreator_3
Note: Compiles the full type / example varchar(20) / or numeric(29,8)
AttributeCreator_3
    ATTR_TABLE = SET_TO SQLFieldType = @Value(SQLFieldType)@Value(_FieldTypeDetails)
    -> AttributeRemover
AttributeCreator_2
    ATTR_TABLE = SET_TO _FieldTypeDetails
    -> AttributeValueMapper_2
AttributeValueMapper_2
    DIRECTION = Forward (Source To Destination)
    LUT = fme_int32,int,fme_int64,bigint,fme_uint64,bigint,fme_uint32,int,fme_int16,int,fme_uint16,int,fme_boolean,char(1) ,fme_int8,smallint,fme_uint8,smallint,fme_real32,float,fme_real64,float,fme_datetime,varchar(20),fme_date,varchar(20)
    SRC = FieldType
    VAL_ATTR = SQLFieldType
    -> AttributeRemover
AttributeRemover
    LIST_ATTRS = _TypeParts{}
    REMOVE_ATTRS = _FieldTypeDetails,_first_match
    -> Output (output)

FME custom transformer CreateFieldsForTSQLJob

Parameters:
- FIELDS =
- FILEID =

Initiator (input)
    -> FlattenJsonFields
Note: Insert/update fields into SQL DW
SQLExecutor_5
    COMBINE_ATTRS = Result Attributes Only
    COMBINE_GEOM = Initiator Geometry Only
    DATASET = CubeManager
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = CubeManager
    MSSQL_ADO_QUERY_FEATURE_TYPES_FOR_MERGE_FILTERS = Yes
    SQL_STATEMENT:
      FME_SQL_DELIMITER ;
      EXEC [dbo].[InsertFieldIntoDimensionFields] @Value(FileId),'@Value(FieldName)','@Value(FieldAlias)','@Value(FieldType)',0,NULL,NULL;
      UPDATE FIELDS
          SET FieldOrder = @Value(json_index)
      WHERE FileId = @Value(FileId)
      AND FieldName = '@Value(FieldName)';
    INITIATOR -> Aggregator_4
Note: Group Fieldnames together
Aggregator_4
    ACCUM_ATTRS_NAME = Use Attributes From One Feature
    AGGREGATE_TYPE = Homogeneous Collection (If Possible)
    CONCAT_ATTRS = FieldName
    MODE = Geometry - Assemble One Level
    ORDERED = No
    SEP = ','
    AGGREGATE -> SQLExecutor_4 [INITIATOR]
Note: Remove Fields
SQLExecutor_4
    COMBINE_ATTRS = Result Attributes Only
    COMBINE_GEOM = Initiator Geometry Only
    DATASET = CubeManager
    FORMAT = MSSQL_ADO
    MSSQL_ADO_COMMAND_TIMEOUT = 30
    MSSQL_ADO_CREATE_FEATURE_TABLES_FROM_DATA = Yes
    MSSQL_ADO_NAMED_CONNECTION = CubeManager
    MSSQL_ADO_QUERY_FEATURE_TYPES_FOR_MERGE_FILTERS = Yes
    SQL_STATEMENT:
      DELETE [dbo].[fields]
      WHERE FileId = @Value(FileId)
      AND dbo.fields.FieldName not in ('@Value(FieldName)')
Continue (output)

Bookmark: Parse fields into an array
FlattenJsonFields: JSONFlattener
    ERROR_LIST_ATTR = _json_error
    JSON_DOCUMENT = @Value(fields)
    READ_FROM_FILE = NO
    RECURSIVE = Yes
    -> JsonNotEmpty
JsonNotEmpty: Tester
    BOOL_OP = OR
    COMPOSITE_TEST = 1
    TEST_CLAUSE = TEST @Value(fields) != []
    TEST_MODE = TEST
    PASSED -> JSONFragmenter
    FAILED -> Continue (output)
JSONFragmenter
    EXPLODE_FORMAT = JSON
    EXTRACT_ATTR = No
    JSON_ATTR = fields
    JSON_QUERY = json[*]
    READ_FROM_FILE = NO
    REJECT_EMPTY_LISTS = YES
    FRAGMENTS -> JSONExtractor_3
JSONExtractor_3
    EXTRACT_QUERY_TABLE = FieldName json["col_name"] FieldType json["data_type"] FieldAlias json["col_name"]
    JSON_DOCUMENT = @Value(fields)
    READ_FROM_FILE = NO
    EVALUATED -> StringToText
Note: If field type is string change it to text
StringToText: AttributeCreator
    ATTR_TABLE = SET_TO FieldType = FME_CONDITIONAL:DEFAULT_VALUE'@Value(FieldType)'BOOL_OP;OR;COMPOSITE_TEST;1;TEST @Value(FieldType) = string'text'FME_NUM_CONDITIONS2___
    -> SQLExecutor_5 [INITIATOR]
