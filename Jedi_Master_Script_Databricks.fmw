FME workspace Jedi_Master_Script_Databricks.fmw
Title: JEDI Orgestrator initiating every other background process
Description: This scripts looks into the database for new dimensions, cubes or any other task related and executes the corresponding workspaces.
Usage: A schedule runs this script on regular intervals inside the FME Server. The script must be configured to run only once at a time.
History: 01/08/2016,Jan Bliki,Initial creation,02/09/2016,Jan Bliki,Add the .TDS creation as additional task

Parameters:
- httpserver =

Note: NOTE: / Be aware that these blocks do not run in a sequence. They execute other workpaces and are picked up the next time this workspace runs. Status flags in the database tell this workspace what needs to run and what has already executed.
Note: Wait untill all subprocesses finish
FeatureHolder
    -> SQLExecutor_3 [INITIATOR]
Note: Tell database job is finished
SQLExecutor_3
    COMBINE_ATTRS = Result Attributes Only
    COMBINE_GEOM = Initiator Geometry Only
    DATASET = CubeManager
    FORMAT = MSSQL_ADO
    MSSQL_ADO_COMMAND_TIMEOUT = 30
    MSSQL_ADO_NAMED_CONNECTION = CubeManager
    MSSQL_ADO_QUERY_FEATURE_TYPES_FOR_MERGE_FILTERS = Yes
    SQL_STATEMENT:
      -- Update JediMasterJobId
      Update dbo.GeneralInfo
          set AttributeValue = 'none'
         where AttributeName = 'JediMasterJobId';

Bookmark: TIME STAMP LAST RUN INTO DATABASE
Note: Tell database when we run this workspace the last time.
RunOnlyOnce
    Initiator -> FMEServerJobSubmitter
    Initiator -> Create_Cube [Initiator]
    Initiator -> Source_To_Azure [Initiator]
    Initiator -> Lookup_Source_to_Azure [Initiator]

Bookmark: SYNC [DIMENSIONCONVERTERS]
Note: Find all Workspaces inside "Cube Dimension Workspaces" / -Repository and store these inside / the SQL-Table [DimensionConverters]
FMEServerJobSubmitter
    BLOCKING = Yes
    PRIORITY = 80
    PROCESSING_MODE = In Sequence
    REPOSITORY = Cube WebTools
    SERVER_CONNECTION = diaz FME Server
    WORKSPACE_NAME = UpdateDimensionConvertersTable.fmw
    SUMMARY -> FMEServerJobSubmitter_3

Bookmark: DELETE ENTITIES
Note: Call for deting entities and related files and databricks / conetent
FMEServerJobSubmitter_3 [off]
    BLOCKING = Yes
    PRIORITY = 80
    PROCESSING_MODE = In Sequence
    REPOSITORY = JEDI_SingleProcess
    SERVER_CONNECTION = diaz FME Server
    WORKSPACE_NAME = R2D2_Cleanup_databricks.fmw
    SUMMARY -> FMEServerJobSubmitter_2

Bookmark: CHEK JOBS IN FME SERVER
Note: Check all JobId's in the database and validate / if they are still executing on FME Server. / If not we report an error.
FMEServerJobSubmitter_2
    BLOCKING = Yes
    PRIORITY = 80
    PROCESSING_MODE = In Sequence
    REPOSITORY = Cube WebTools
    SERVER_CONNECTION = diaz FME Server
    WORKSPACE_NAME = ReportStatusToCubeManager.fmw
    WORKSPACE_PARAMETERS = FMEServer string http://fme.discomap.eea.europa.eu
    JOB_FAILED -> FeatureHolder
    SUMMARY -> FeatureHolder
    <REJECTED> -> FeatureHolder

Bookmark: STEP1: UPLOAD SOURCE
Note: All files that are validated are transfered towards the cloud as a backup. This only happens when it is a new file. / Use the following procedure to reset the process. / exec [dbo].[resetAzureSourceUpload] <FileId>
Source_To_Azure
    httpserver = $(httpserver)
    Continue -> Source_To_GRID [Initiator]

Bookmark: STEP2:SOURCE FORMAT TO GRID
Note: Validate source file and process dimension from source into GRID-file. / Executes the validation and creation of a dimension. / Use the following procedure to reset the process. / exec [dbo].[resetAzureDimensionProcess] <FileId>
Source_To_GRID
    httpserver = $(httpserver)
    Continue -> GRID_To_Azure [Initiator]

Bookmark: STEP3: UPLOAD GRID (for vectors only)
Note: All dimensions files that have been prepared will be send to Azure. / Use the following procedure to reset the process. / exec [dbo].[resetAzureDimensionUpload] <FileId>
GRID_To_Azure: GRID To Azure
    httpserver = $(httpserver)
    Continue -> Azure_Blob_to_Databricks [Initiator]

Bookmark: STEP4: AZURE BLOB TO SQL SW (for vectors only)
Note: For every dimension file stored inside the SQL DW we will have a representative table / D_<Dimension name>_<Creation date> / Reset this process using the following SQL-Procedure: / exec resetSQLDWCreation <FileId>
Azure_Blob_to_Databricks: Azure Blob to SQL DW
    httpserver = $(httpserver)
    -> FeatureHolder
    Rejected -> FeatureHolder
    Continue -> FeatureHolder

Bookmark: StepA: CREATE CUBE
Note: Generate the tables inside the SQL Data Warehouse / F_<TableName>_<CreationDate> : Every single GRIDCELL and it's related attributes / C_<TableName>_<CreationDate> : Aggregated on code attributes / CL_<TableName>_<CreationDate>: Aggregated table + lookup fields / M_<TableName>_<CreationDate>: Relation between coördinate and GridNum to every aggregated RecordId in CL_ or C_ / Use the following SQL Procedure to reset this process / exec resetCUBE <CubeId>
Create_Cube: Create Cube
    httpserver = $(httpserver)
    Continue -> MoveLocal [Initiator]

Bookmark: STEP B: MOVE TO LOCAL DB
Note: This process will move the F_ and C_table / to a local database that is online at all times
MoveLocal
    httpserver = $(httpserver)
    Continue -> Tableau_TDS_Generation [Initiator]

Bookmark: STEP C: CREATE TDS
Note: This process will generate a .tds file for Tableau. The file is stored inside Azure and as well into the generic "Data source" on Common Workspace. / <CubeName>.tds / Use the following SQL Procedure to reset this process / exec resetCUBE <CubeId>
Tableau_TDS_Generation: Tableau TDS Generation
    httpserver = $(httpserver)
    -> FeatureHolder
    Rejected -> FeatureHolder
    Continue -> FeatureHolder

Bookmark: STEP1: LOOKUP SOURCE TO AZURE
Note: All files that are validated can be transfered towards the cloud
Lookup_Source_to_Azure: Lookup Source to Azure
    AUTH_NAMED_CONNECTION = diaz FME Server
    httpserver = $(httpserver)
    Continue -> Lookup_into_SQL_DW [Initiator]

Bookmark: STEP2: LOOKUP TO SQL DW
Note: All files that are validated can be transfered towards the cloud
Lookup_into_SQL_DW: Lookup into SQL DW
    AUTH_NAMED_CONNECTION = diaz FME Server
    httpserver = $(httpserver)
    -> FeatureHolder
    Rejected -> FeatureHolder
    Continue -> FeatureHolder

FME custom transformer LookupJobSubmitter

Parameters:
- AUTH_NAMED_CONNECTION =
- FMECONVERSIONPROCESS =
- LookupId =
- Repository =
- httpserver =

Note: We can't use the FMEServerJob Sumbitter for two reasons. / - You can't dynamicaly provide different workspaces to that transormer. / - The Notiication services do not run when you use the FMEServerJobSubmitter.
Input (input)
    -> AttributeCreator
Note: Compile the URL
AttributeCreator
    ATTR_TABLE = SET_TO JobSubmitterUrl = $(httpserver)/fmejobsubmitter/$(Repository)/@Value(FmeConversionProcess)?LookupId=$(LookupId)&opt_showresult=false&opt_servicemode=async&opt_responseformat=json
    -> HTTPCaller
HTTPCaller
    AUTH_METHOD = Named Web Connection
    AUTH_NAMED_CONNECTION = $(AUTH_NAMED_CONNECTION)
    CONNECTION_TIMEOUT_LENGTH = 60
    ERROR_ATTR = _error
    FOLLOW_REDIRECTS = Yes
    HTTP_METHOD = GET
    RESPONSE_HEADER_LIST_ATTR = _headers
    SAVE_FILE = Attribute
    STATUS_CODE_ATTR = _http_status_code
    TARGET_ATTR = _response_body
    TARGET_ATTR_ENCODING = utf-8
    TARGET_URL = @Value(JobSubmitterUrl)
    TRANSFER_TIMEOUT_LENGTH = 90
    USE_COOKIES = No
    VERIFY_SSL_CERTIFICATES = Yes
    -> JSONExtractor
    <REJECTED> -> Failed (output)
JSONExtractor
    EXTRACT_QUERY_TABLE = _job_id JSON["serviceResponse"]["jobID"] _status JSON["serviceResponse"]["statusInfo"]["status"]
    JSON_DOCUMENT = @Value(_response_body)
    EVALUATED -> TestFilter
    <REJECTED> -> Failed (output)
TestFilter
    DEFAULT_VALUE = failed
    TEST_LIST = BOOL_OP,OR,COMPOSITE_TEST,<Unused>,TEST_CLAUSE,"TEST @Value(_status) = success",success
    success -> Succeeded (output)
    failed -> Failed (output)
Succeeded (output)
Failed (output)

FME custom transformer Lookup Source to Azure

Parameters:
- AUTH_NAMED_CONNECTION =
- httpserver =

Initiator (input)
    -> SQLExecutor_19 [INITIATOR]
    -> Continue (output)
Note: [FMEJobIdSourceUploaded] is null
SQLExecutor_19
    COMBINE_ATTRS = Result Attributes Only
    COMBINE_GEOM = Initiator Geometry Only
    DATASET = CubeManager
    EXPOSED_ATTRIBUTE_LIST = LookupId SourceFile
    FORMAT = MSSQL_ADO
    MSSQL_ADO_COMMAND_TIMEOUT = 30
    MSSQL_ADO_CREATE_FEATURE_TABLES_FROM_DATA = Yes
    MSSQL_ADO_NAMED_CONNECTION = CubeManager
    MSSQL_ADO_QUERY_FEATURE_TYPES_FOR_MERGE_FILTERS = Yes
    SQL_STATEMENT:
      select   dbo.[Lookups].[LookupId]
              ,dbo.[Lookups].[SourceFile]
      from dbo.[Lookups]
      where isnull([FMEJobIdUploaded],0) =0
      and SourceFile is not null and deleteflag=0
    RESULT -> FileSystemDeleteMoveCopyExist_4 [FileName]
    <REJECTED> -> Rejected (output)
FileSystemDeleteMoveCopyExist_4
    Action = EXIST
    FILEINPUT = @Value(SourceFile)
    Success -> LookupJobSubmitter
    NotFound -> SQLExecutor_21 [INITIATOR]
    Failed -> Rejected (output)
LookupJobSubmitter
    AUTH_NAMED_CONNECTION = $(AUTH_NAMED_CONNECTION)
    FMECONVERSIONPROCESS = LookupFilesToAzureDatabricks.fmw
    LookupId = @Value(LookupId)
    Repository = Cube WebTools
    httpserver = $(httpserver)
    Succeeded -> SQLExecutor_20 [INITIATOR]
    Failed -> Rejected (output)
Note: Tell database what JobId is doing the work
SQLExecutor_20
    COMBINE_ATTRS = Result Attributes Only
    COMBINE_GEOM = Initiator Geometry Only
    DATASET = CubeManager
    FORMAT = MSSQL_ADO
    MSSQL_ADO_COMMAND_TIMEOUT = 30
    MSSQL_ADO_NAMED_CONNECTION = CubeManager
    MSSQL_ADO_QUERY_FEATURE_TYPES_FOR_MERGE_FILTERS = Yes
    SQL_STATEMENT:
      update dbo.Lookups
          set FMEJobIdUploaded = @Value(_job_id)
      where LookupId = @Value(LookupId)
    INITIATOR -> Output (output)
    <REJECTED> -> Rejected (output)
Note: We can't find the source file, abort process
SQLExecutor_21
    COMBINE_ATTRS = Result Attributes Only
    COMBINE_GEOM = Initiator Geometry Only
    DATASET = CubeManager
    FORMAT = MSSQL_ADO
    MSSQL_ADO_COMMAND_TIMEOUT = 30
    MSSQL_ADO_NAMED_CONNECTION = CubeManager
    MSSQL_ADO_QUERY_FEATURE_TYPES_FOR_MERGE_FILTERS = Yes
    SQL_STATEMENT:
      update dbo.Lookups
          set ErrorMessages = 'ERROR: Can''t find source file ("@Value(SourceFile)")... Upload to cloud is not possible...'
      where [LookupId] = @Value(LookupId)
    INITIATOR -> Output (output)
    <REJECTED> -> Rejected (output)
Output (output)
Rejected (output)
Continue (output)

FME custom transformer Tableau TDS Generation

Parameters:
- httpserver =

Initiator (input)
    -> SQLExecutor_24 [INITIATOR]
Note: dbo.[Cubes].[ProcessCube]=1 / and dbo.[Cubes].[FMEJobIdCubeStatus] =1 / and dbo.[Cubes].[FMEJobIdTDSGenerator] is null
SQLExecutor_24
    COMBINE_ATTRS = Result Attributes Only
    COMBINE_GEOM = Initiator Geometry Only
    DATASET = CubeManager
    EXPOSED_ATTRIBUTE_LIST = CubeId
    FORMAT = MSSQL_ADO
    MSSQL_ADO_COMMAND_TIMEOUT = 30
    MSSQL_ADO_CREATE_FEATURE_TABLES_FROM_DATA = Yes
    MSSQL_ADO_NAMED_CONNECTION = CubeManager
    MSSQL_ADO_QUERY_FEATURE_TYPES_FOR_MERGE_FILTERS = Yes
    SQL_STATEMENT:
      --
      -- Find records in Cubes that have been processed in the DWH but did not have a .TDS file generated.
      --
      --
      select dbo.Cubes.CubeId
      from dbo.[Cubes]
      where dbo.[Cubes].[ProcessCube]=1
        and dbo.[Cubes].[FMEJobIdCubeStatus] =1
        and dbo.[Cubes].[FMEJobIdMovetoLocalDBStatus] = 1
        and dbo.[Cubes].[FMEJobIdTDSGenerator] is null
        and DeleteFlag=0
    RESULT -> DynamicJobSubmitterCubes_2
    INITIATOR -> Tester
    <REJECTED> -> Rejected (output)
Note: C_Table.tds-table
DynamicJobSubmitterCubes_2
    CUBEID = @Value(CubeId)
    FMECONVERSIONPROCESS = TableauTDS_writer.fmw
    Repository = Cube WebTools
    TableName = C
    httpserver = $(httpserver)
    Succeeded -> DynamicJobSubmitterCubes_3
    Succeeded -> Output (output)
    Failed -> Rejected (output)
Note: F_Table.tds-table
DynamicJobSubmitterCubes_3 [off]
    CUBEID = @Value(CubeId)
    FMECONVERSIONPROCESS = TableauTDS_writer.fmw
    Repository = Cube WebTools
    TableName = F
    httpserver = $(httpserver)
    Succeeded -> Output (output)
    Failed -> Rejected (output)
Output (output)
Rejected (output)
Tester
    BOOL_OP = OR
    COMPOSITE_TEST = 1
    TEST_CLAUSE = TEST @Value(_matched_records) = 0
    TEST_MODE = TEST
    PASSED -> Continue (output)
Continue (output)

FME custom transformer Source_To_Azure

Parameters:
- httpserver =

Initiator (input)
    -> SQLExecutor_2 [INITIATOR]
    -> Continue (output)
Note: Validated=1 / and [FMEJobIdSourceUploaded] is null
SQLExecutor_2
    COMBINE_ATTRS = Result Attributes Only
    COMBINE_GEOM = Initiator Geometry Only
    DATASET = CubeManager
    EXPOSED_ATTRIBUTE_LIST = FileId SourceFile SourceUploadFME
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = CubeManager
    MSSQL_ADO_QUERY_FEATURE_TYPES_FOR_MERGE_FILTERS = Yes
    SQL_STATEMENT:
      select   dbo.[Files].[FileId]
              ,dbo.[Files].[SourceFile]
      		,case
      			when [FmeConversionProcess] = 'CreateDatabricksDimensionFieldParts.fmw' then 'OptimiseAndUploadDimensionFieldParts.fmw'
      		    else  'SourceFilesToAzureDatabricks.fmw'
      		END as SourceUploadFME
      from CubeDimensions
      left join [dbo].files
          on [dbo].[CubeDimensions].[CubeDimensionId]  = dbo.[Files].CubeDimensionId
      where  ISNULL(dbo.[Files].[FMEJobIdSourceUploaded],0) = 0
      	and ISNULL(dbo.[Files].[SourceFile],'') !=''
          and CubeDimensions.DeleteFlag=0
    RESULT -> FileSystemDeleteMoveCopyExist_2 [FileName]
    <REJECTED> -> Rejected (output)
FileSystemDeleteMoveCopyExist_2
    Action = EXIST
    FILEINPUT = @Value(SourceFile)
    Success -> DynamicJobSubmitter_3
    NotFound -> SQLExecutor_15 [INITIATOR]
DynamicJobSubmitter_3
    FILEID = @Value(FileId)
    FMECONVERSIONPROCESS = @Value(SourceUploadFME)
    Repository = Cube Dimension Workspaces
    httpserver = $(httpserver)
    Succeeded -> SQLExecutor_5 [INITIATOR]
    Failed -> Rejected (output)
Note: Tell database what JobId is doing the work
SQLExecutor_5
    COMBINE_ATTRS = Result Attributes Only
    COMBINE_GEOM = Initiator Geometry Only
    DATASET = CubeManager
    FORMAT = MSSQL_ADO
    MSSQL_ADO_COMMAND_TIMEOUT = 30
    MSSQL_ADO_CREATE_FEATURE_TABLES_FROM_DATA = Yes
    MSSQL_ADO_NAMED_CONNECTION = CubeManager
    MSSQL_ADO_QUERY_FEATURE_TYPES_FOR_MERGE_FILTERS = Yes
    SQL_STATEMENT:
      update dbo.Files
          set FMEJobIdSourceUploaded = @Value(_job_id)
      where FileId = @Value(FileId)
    INITIATOR -> Output (output)
Note: We can't find the source file, abort process
SQLExecutor_15
    COMBINE_ATTRS = Result Attributes Only
    COMBINE_GEOM = Initiator Geometry Only
    DATASET = CubeManager
    FORMAT = MSSQL_ADO
    MSSQL_ADO_COMMAND_TIMEOUT = 30
    MSSQL_ADO_CREATE_FEATURE_TABLES_FROM_DATA = Yes
    MSSQL_ADO_NAMED_CONNECTION = CubeManager
    MSSQL_ADO_QUERY_FEATURE_TYPES_FOR_MERGE_FILTERS = Yes
    SQL_STATEMENT:
      update dbo.Files
          set ErrorMessages = 'ERROR: Can''t find source file ("@Value(SourceFile)")... Upload to cloud is not possible...'
      where FileId = @Value(FileId)
    INITIATOR -> Output (output)
    <REJECTED> -> Rejected (output)
Output (output)
Rejected (output)
Continue (output)

FME custom transformer DynamicJobSubmitterCubes

Parameters:
- CUBEID =
- FMECONVERSIONPROCESS =
- Repository =
- TableName =
- httpserver =

Input (input)
    -> TestFilter_2
Note: We can't use the FMEServerJob Sumbitter for two reasons. / - You can't dynamicaly provide different workspaces to that transformer. / - The Notiication services do not run when you use the FMEServerJobSubmitter.
TestFilter_2
    DEFAULT_VALUE = CUBE
    TEST_LIST = BOOL_OP,OR,COMPOSITE_TEST,<Unused>,TEST_CLAUSE,"TEST $(FMECONVERSIONPROCESS) = TableauTDS_writer.fmw",TDS
    TDS -> AttributeCreator
    CUBE -> AttributeCreator_2
Note: Compile the URL
AttributeCreator
    ATTR_TABLE = SET_TO JobSubmitterUrl = $(httpserver)/fmejobsubmitter/$(Repository)/@Value(FmeConversionProcess)?CubeId=$(CUBEID)&TableOutput=$(TableName)&opt_showresult=false&opt_servicemode=async&opt_responseformat=json
    -> HTTPCaller
Note: Compile the URL
AttributeCreator_2
    ATTR_TABLE = SET_TO JobSubmitterUrl = $(httpserver)/fmejobsubmitter/$(Repository)/@Value(FmeConversionProcess)?CubeId=$(CUBEID)&opt_showresult=false&opt_servicemode=async&opt_responseformat=json
    -> HTTPCaller
HTTPCaller
    AUTH_METHOD = Named Web Connection
    AUTH_NAMED_CONNECTION = esparza FME Server
    CONNECTION_TIMEOUT_LENGTH = 60
    ERROR_ATTR = _error
    FOLLOW_REDIRECTS = Yes
    HTTP_METHOD = GET
    RESPONSE_HEADER_LIST_ATTR = _headers
    SAVE_FILE = Attribute
    STATUS_CODE_ATTR = _http_status_code
    TARGET_ATTR = _response_body
    TARGET_ATTR_ENCODING = utf-8
    TARGET_URL = @Value(JobSubmitterUrl)
    TRANSFER_TIMEOUT_LENGTH = 90
    USE_COOKIES = No
    VERIFY_SSL_CERTIFICATES = Yes
    -> JSONExtractor
    <REJECTED> -> Failed (output)
JSONExtractor
    EXTRACT_QUERY_TABLE = _job_id JSON["serviceResponse"]["jobID"] _status JSON["serviceResponse"]["statusInfo"]["status"]
    JSON_DOCUMENT = @Value(_response_body)
    EVALUATED -> TestFilter
    <REJECTED> -> Failed (output)
TestFilter
    DEFAULT_VALUE = failed
    TEST_LIST = BOOL_OP,OR,COMPOSITE_TEST,<Unused>,TEST_CLAUSE,"TEST @Value(_status) = success",success
    success -> Succeeded (output)
    failed -> Failed (output)
Succeeded (output)
Failed (output)

FME custom transformer Lookup into SQL DW

Parameters:
- AUTH_NAMED_CONNECTION =
- httpserver =

Initiator (input)
    -> SQLExecutor_22 [INITIATOR]
Note: [FMEJobIdSQLDWCreated] is null / and [FMEJobIdUploadedStatus] = 1
SQLExecutor_22
    COMBINE_ATTRS = Result Attributes Only
    COMBINE_GEOM = Initiator Geometry Only
    DATASET = CubeManager
    EXPOSED_ATTRIBUTE_LIST = LookupId SourceFile
    FORMAT = MSSQL_ADO
    MSSQL_ADO_COMMAND_TIMEOUT = 30
    MSSQL_ADO_CREATE_FEATURE_TABLES_FROM_DATA = Yes
    MSSQL_ADO_NAMED_CONNECTION = CubeManager
    MSSQL_ADO_QUERY_FEATURE_TYPES_FOR_MERGE_FILTERS = Yes
    SQL_STATEMENT:
      select  dbo.[Lookups].[LookupId]
              ,dbo.[Lookups].[SourceFile]
      from dbo.[Lookups]
      where isnull([FMEJobIdSQLDWCreated],0) =0
      and [FMEJobIdUploadedStatus] = 1 and deleteflag=0
    RESULT -> LookupJobSubmitter_2
    INITIATOR -> Tester
    <REJECTED> -> Rejected (output)
LookupJobSubmitter_2
    AUTH_NAMED_CONNECTION = $(AUTH_NAMED_CONNECTION)
    FMECONVERSIONPROCESS = CreateLookupTableInsideDatabricks.fmw
    LookupId = @Value(LookupId)
    Repository = Cube WebTools
    httpserver = $(httpserver)
    Succeeded -> SQLExecutor_23 [INITIATOR]
    Failed -> Rejected (output)
Note: Tell database what JobId is doing the work
SQLExecutor_23
    COMBINE_ATTRS = Result Attributes Only
    COMBINE_GEOM = Initiator Geometry Only
    DATASET = CubeManager
    FORMAT = MSSQL_ADO
    MSSQL_ADO_COMMAND_TIMEOUT = 30
    MSSQL_ADO_NAMED_CONNECTION = CubeManager
    MSSQL_ADO_QUERY_FEATURE_TYPES_FOR_MERGE_FILTERS = Yes
    SQL_STATEMENT:
      update dbo.Lookups
          set  [FMEJobIdSQLDWCreated] = @Value(_job_id)
      where LookupId = @Value(LookupId)
    INITIATOR -> Output (output)
    <REJECTED> -> Rejected (output)
Output (output)
Rejected (output)
Tester
    BOOL_OP = OR
    COMPOSITE_TEST = 1
    TEST_CLAUSE = TEST @Value(_matched_records) = 0
    TEST_MODE = TEST
    PASSED -> Continue (output)
Continue (output)

FME custom transformer Source_To_GRID

Parameters:
- httpserver =

Initiator (input)
    -> SQLExecutor_6 [INITIATOR]
    -> Continue (output)
Note: dbo.[Files].[FMEJobIdDimensionProcess] is null
SQLExecutor_6
    COMBINE_ATTRS = Result Attributes Only
    COMBINE_GEOM = Initiator Geometry Only
    DATASET = CubeManager
    EXPOSED_ATTRIBUTE_LIST = AzureSourceFile FileId FmeConversionProcess FMEJediTemp SourceFile
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = CubeManager
    MSSQL_ADO_QUERY_FEATURE_TYPES_FOR_MERGE_FILTERS = Yes
    SQL_STATEMENT:
      select  dbo.[Files].[FileId],
      			[dbo].[CubeDimensions].[FmeConversionProcess],
              dbo.[Files].[SourceFile],
              dbo.[Files].[AzureSourceFile],
              (select top 1 AttributeValue from dbo.[GeneralInfo] where AttributeName = 'FMEJediTemp') as FMEJediTemp
      from CubeDimensions
      left join [dbo].files
          on [dbo].[CubeDimensions].[CubeDimensionId]  = dbo.[Files].CubeDimensionId
      where
        ISNULL(dbo.[Files].[FMEJobIdDimensionProcess],0) = 0
      and    ISNULL(FMEJobIdSourceUploadStatus,0) !=0
      and	ISNULL(dbo.[Files].[AzureSourceFile],'') !=''
      and CubeDimensions.DeleteFlag=0
    RESULT -> DynamicJobSubmitter
    <REJECTED> -> Rejected (output)
DynamicJobSubmitter
    FILEID = @Value(FileId)
    FMECONVERSIONPROCESS = @Value(FmeConversionProcess)
    Repository = Cube Dimension Workspaces
    httpserver = $(httpserver)
    Succeeded -> SQLExecutor_9 [INITIATOR]
    Failed -> Rejected (output)
Note: Tell database what JobId is doing the work
SQLExecutor_9
    COMBINE_ATTRS = Result Attributes Only
    COMBINE_GEOM = Initiator Geometry Only
    DATASET = CubeManager
    FORMAT = MSSQL_ADO
    MSSQL_ADO_COMMAND_TIMEOUT = 30
    MSSQL_ADO_CREATE_FEATURE_TABLES_FROM_DATA = Yes
    MSSQL_ADO_NAMED_CONNECTION = CubeManager
    MSSQL_ADO_QUERY_FEATURE_TYPES_FOR_MERGE_FILTERS = Yes
    SQL_STATEMENT:
      update dbo.Files
          set FMEJobIdValidator = @Value(_job_id),
              FMEJobIdDimensionProcess = @Value(_job_id)
      where FileId = @Value(FileId)
    INITIATOR -> Output (output)
    <REJECTED> -> Rejected (output)
Output (output)
Rejected (output)
Continue (output)

FME custom transformer Create Cube

Parameters:
- httpserver =

Initiator (input)
    -> SQLExecutor_17 [INITIATOR]
    -> Continue (output)
Note: dbo.[CUBES].ProcessCube=1 and FMEJobIdCubeCompiler is Null
SQLExecutor_17
    COMBINE_ATTRS = Result Attributes Only
    COMBINE_GEOM = Initiator Geometry Only
    DATASET = CubeManager
    EXPOSED_ATTRIBUTE_LIST = CubeId
    FORMAT = MSSQL_ADO
    MSSQL_ADO_COMMAND_TIMEOUT = 30
    MSSQL_ADO_CREATE_FEATURE_TABLES_FROM_DATA = Yes
    MSSQL_ADO_NAMED_CONNECTION = CubeManager
    MSSQL_ADO_QUERY_FEATURE_TYPES_FOR_MERGE_FILTERS = Yes
    SQL_STATEMENT:
      select dbo.Cubes.CubeId
      from dbo.[Cubes]
      where dbo.[Cubes].[ProcessCube]=1
          and ISNULL(dbo.[Cubes].[FMEJobIdCubeCompiler],0) =0
          and DeleteFlag=0
    RESULT -> DynamicJobSubmitter
    <REJECTED> -> Rejected (output)
DynamicJobSubmitter: DynamicJobSubmitterCubes
    CUBEID = @Value(CubeId)
    FMECONVERSIONPROCESS = CreateCubeByViewAndTableDatabricks_3Res.fmw
    Repository = Cube WebTools
    httpserver = $(httpserver)
    Succeeded -> SQLExecutor_18 [INITIATOR]
    Failed -> Rejected (output)
Note: Tell database what JobId is doing the work
SQLExecutor_18
    COMBINE_ATTRS = Result Attributes Only
    COMBINE_GEOM = Initiator Geometry Only
    DATASET = CubeManager
    FORMAT = MSSQL_ADO
    MSSQL_ADO_COMMAND_TIMEOUT = 30
    MSSQL_ADO_CREATE_FEATURE_TABLES_FROM_DATA = Yes
    MSSQL_ADO_NAMED_CONNECTION = CubeManager
    MSSQL_ADO_QUERY_FEATURE_TYPES_FOR_MERGE_FILTERS = Yes
    SQL_STATEMENT:
      update dbo.Cubes
          set FMEJobIdCubeCompiler = @Value(_job_id),
              FMEJobIdCubeCompilerDate = getDate()
      where CubeId = @Value(CubeId)
    RESULT -> Output (output)
    <REJECTED> -> Rejected (output)
Output (output)
Rejected (output)
Continue (output)

FME custom transformer MoveLocal

Parameters:
- httpserver =

Initiator (input)
    -> SQLExecutor_17 [INITIATOR]
    -> Continue (output)
Note: dbo.[Cubes].[ProcessCube]=1 / and dbo.[Cubes].[FMEJobIdCubeCompiler]=1 / and dbo.[Cubes].[FMEJobIdMoveToLocalDB] is null
SQLExecutor_17
    COMBINE_ATTRS = Result Attributes Only
    COMBINE_GEOM = Initiator Geometry Only
    DATASET = CubeManager
    EXPOSED_ATTRIBUTE_LIST = CubeId
    FORMAT = MSSQL_ADO
    MSSQL_ADO_COMMAND_TIMEOUT = 30
    MSSQL_ADO_CREATE_FEATURE_TABLES_FROM_DATA = Yes
    MSSQL_ADO_NAMED_CONNECTION = CubeManager
    MSSQL_ADO_QUERY_FEATURE_TYPES_FOR_MERGE_FILTERS = Yes
    SQL_STATEMENT:
      select dbo.Cubes.CubeId
      from dbo.[Cubes]
      where dbo.[Cubes].[ProcessCube]=1
          and dbo.[Cubes].[FMEJobIdCubeStatus]=1
          and isnull(dbo.[Cubes].[FMEJobIdMoveToLocalDB],0) =0
          and DeleteFlag=0
    RESULT -> DynamicJobSubmitterMoveToLocal
    <REJECTED> -> Rejected (output)
DynamicJobSubmitterMoveToLocal: DynamicJobSubmitterCubes
    CUBEID = @Value(CubeId)
    FMECONVERSIONPROCESS = BringResultToLocalDBDatabricks.fmw
    Repository = Cube WebTools
    httpserver = $(httpserver)
    Succeeded -> SQLExecutor_18 [INITIATOR]
    Failed -> Rejected (output)
Note: Tell database what JobId is doing the work
SQLExecutor_18
    COMBINE_ATTRS = Result Attributes Only
    COMBINE_GEOM = Initiator Geometry Only
    DATASET = CubeManager
    FORMAT = MSSQL_ADO
    MSSQL_ADO_COMMAND_TIMEOUT = 30
    MSSQL_ADO_NAMED_CONNECTION = CubeManager
    MSSQL_ADO_QUERY_FEATURE_TYPES_FOR_MERGE_FILTERS = Yes
    SQL_STATEMENT:
      update dbo.Cubes
          set [FMEJobIdMoveToLocalDB] = @Value(_job_id),
              [FMEJobIdMoveToLocalDBDate] = getDate()
      where CubeId = @Value(CubeId)
    RESULT -> Output (output)
    <REJECTED> -> Rejected (output)
Output (output)
Rejected (output)
Continue (output)

FME custom transformer RunOnlyOnce

Note: Only execute if job is not running
SQLCreator
    DATASET = CubeManager
    FORMAT = MSSQL_ADO
    MSSQL_ADO_COMMAND_TIMEOUT = 30
    MSSQL_ADO_NAMED_CONNECTION = CubeManager
    MSSQL_ADO_QUERY_FEATURE_TYPES_FOR_MERGE_FILTERS = Yes
    SQL_STATEMENT:
      --
      -- Only continue if we don't have this job already in the queue or it was not executed longer then 10 minutes ago
      --
      SELECT 1 as Ok
      FROM [dbo].[GeneralInfo] as JID
      INNER JOIN [dbo].[GeneralInfo] as TS
      	on TS.AttributeName= 'JediMasterTimeStamp'
      WHERE  JID.AttributeName = 'JediMasterJobId'
      		AND (   JID.AttributeValue = 'none'
      			 OR JID.AttributeValue = ''
      			 OR JID.AttributeValue IS NULL
      		     OR datediff(minute,convert(datetime,TS.AttributeValue),getdate())  > 10
      			 )
    RESULT -> TimeStamper
TimeStamper
    FMT = ^A ^d-^b-^Y at ^H:^M:^S
    TIME_ATTR = _timestamp
    -> Store_Time_in_SQL [INITIATOR]
Note: Remember time and JobId
Store_Time_in_SQL: SQLExecutor
    COMBINE_ATTRS = Result Attributes Only
    COMBINE_GEOM = Initiator Geometry Only
    DATASET = CubeManager
    FORMAT = MSSQL_ADO
    MSSQL_ADO_COMMAND_TIMEOUT = 30
    MSSQL_ADO_NAMED_CONNECTION = CubeManager
    MSSQL_ADO_QUERY_FEATURE_TYPES_FOR_MERGE_FILTERS = Yes
    SQL_STATEMENT:
      FME_SQL_DELIMITER ;
      -- Set timestamp of current process executing (For user)
      Update dbo.GeneralInfo
          set AttributeValue = '@Value(_timestamp)'
         where AttributeName = 'FMEServerLastCheck';
      -- Update JediMasterJobId
      Update dbo.GeneralInfo
          set AttributeValue = '$(FME_JOB_ID)'
         where AttributeName = 'JediMasterJobId';
      -- Set timestamp of current process executing
      Update dbo.GeneralInfo
          set AttributeValue = convert(varchar,getdate())
         where AttributeName = 'JediMasterTimeStamp';
    INITIATOR -> Initiator (output)
    INITIATOR -> SQLExecutor_3 [INITIATOR]
Initiator (output)
Note: Tell database job is finished
SQLExecutor_3 [off]
    COMBINE_ATTRS = Result Attributes Only
    COMBINE_GEOM = Initiator Geometry Only
    DATASET = CubeManager
    FORMAT = MSSQL_ADO
    MSSQL_ADO_COMMAND_TIMEOUT = 30
    MSSQL_ADO_NAMED_CONNECTION = CubeManager
    MSSQL_ADO_QUERY_FEATURE_TYPES_FOR_MERGE_FILTERS = Yes
    SQL_STATEMENT:
      -- Update JediMasterJobId
      Update dbo.GeneralInfo
          set AttributeValue = 'none'
         where AttributeName = 'JediMasterJobId';

FME custom transformer DynamicJobSubmitter

Parameters:
- FILEID =
- FMECONVERSIONPROCESS =
- Repository =
- httpserver =
- tmtag =

Input (input)
    -> AttributeCreator
Note: We can't use the FMEServerJob Sumbitter for two reasons. / - You can't dynamicaly provide different workspaces to that transormer. / - The Notiication services do not run when you use the FMEServerJobSubmitter.
Note: Compile the URL
AttributeCreator
    ATTR_TABLE = SET_TO JobSubmitterUrl = $(httpserver)/fmejobsubmitter/$(Repository)/@Value(FmeConversionProcess)?FileId=@Value(FileId)&opt_showresult=false&opt_servicemode=async&opt_responseformat=json
    -> AttributeCreator_2
Note: Add routing tag
AttributeCreator_2
    ATTR_TABLE = SET_TO JobSubmitterUrl = FME_CONDITIONAL:DEFAULT_VALUE'_FME_NO_OP_'BOOL_OP;OR;COMPOSITE_TEST;<Unused>;TEST $(tmtag) ATTRIBUTE_HAS_VALUE _FME_BLANK_STRING_'@Value(JobSubmitterUrl)&tm_tag=$(tmtag)'FME_NUM_CONDITIONS2___
    -> HTTPCaller
HTTPCaller
    AUTH_METHOD = Named Web Connection
    AUTH_NAMED_CONNECTION = esparza FME Server
    CONNECTION_TIMEOUT_LENGTH = 60
    ERROR_ATTR = _error
    FOLLOW_REDIRECTS = Yes
    HTTP_METHOD = GET
    RESPONSE_HEADER_LIST_ATTR = _headers
    SAVE_FILE = Attribute
    STATUS_CODE_ATTR = _http_status_code
    TARGET_ATTR = _response_body
    TARGET_ATTR_ENCODING = utf-8
    TARGET_URL = @Value(JobSubmitterUrl)
    TRANSFER_TIMEOUT_LENGTH = 90
    USE_COOKIES = No
    VERIFY_SSL_CERTIFICATES = Yes
    -> JSONExtractor
    <REJECTED> -> Failed (output)
JSONExtractor
    EXTRACT_QUERY_TABLE = _job_id JSON["serviceResponse"]["jobID"] _status JSON["serviceResponse"]["statusInfo"]["status"]
    JSON_DOCUMENT = @Value(_response_body)
    EVALUATED -> TestFilter
    <REJECTED> -> Failed (output)
TestFilter
    DEFAULT_VALUE = failed
    TEST_LIST = BOOL_OP,OR,COMPOSITE_TEST,<Unused>,TEST_CLAUSE,"TEST @Value(_status) = success",success
    success -> Succeeded (output)
    failed -> Failed (output)
Succeeded (output)
Failed (output)

FME custom transformer GRID To Azure

Parameters:
- httpserver =

Initiator (input)
    -> SQLExecutor_3 [INITIATOR]
    -> Continue (output)
Note: dbo.[Files].[Validated]=1 / and dbo.[Files].[DimensionFile] is not null / and dbo.[Files].[FMEJobIdDimensionUploaded] is null
SQLExecutor_3
    COMBINE_ATTRS = Result Attributes Only
    COMBINE_GEOM = Initiator Geometry Only
    DATASET = CubeManager
    EXPOSED_ATTRIBUTE_LIST = FileId DimensionFile
    FORMAT = MSSQL_ADO
    MSSQL_ADO_COMMAND_TIMEOUT = 30
    MSSQL_ADO_CREATE_FEATURE_TABLES_FROM_DATA = Yes
    MSSQL_ADO_NAMED_CONNECTION = CubeManager
    MSSQL_ADO_QUERY_FEATURE_TYPES_FOR_MERGE_FILTERS = Yes
    SQL_STATEMENT:
      select  dbo.[Files].[FileId]
              ,dbo.[Files].[DimensionFile]
      from dbo.[Files] inner join
      	CubeDimensions on files.CubeDimensionId = CubeDimensions.CubeDimensionId and
                            files.FileId = CubeDimensions.ActiveFile
      where dbo.[Files].[Validated]=1
        and dbo.[Files].[FMEJobIdDimensionProcessStatus] = 1
        and dbo.[Files].[DimensionFile] is not null
        and dbo.[Files].[FMEJobIdDimensionUploaded] is null
        and CubeDimensions.DeleteFlag =0
        and CubeDimensions.FmeConversionProcess != 'CreateDatabricksDimension.fmw'
    RESULT -> FileSystemDeleteMoveCopyExist [FileName]
    <REJECTED> -> Rejected (output)
FileSystemDeleteMoveCopyExist
    Action = EXIST
    FILEINPUT = @Value(DimensionFile)
    Success -> DynamicJobSubmitter_2
    NotFound -> SQLExecutor_14 [INITIATOR]
    Failed -> Rejected (output)
DynamicJobSubmitter_2
    FILEID = @Value(FileId)
    FMECONVERSIONPROCESS = DimensionFilesToAzureDatabricks.fmw
    Repository = Cube WebTools
    httpserver = $(httpserver)
    Succeeded -> SQLExecutor_4 [INITIATOR]
    Failed -> Rejected (output)
Note: Tell database what JobId is doing the work
SQLExecutor_4
    COMBINE_ATTRS = Result Attributes Only
    COMBINE_GEOM = Initiator Geometry Only
    DATASET = CubeManager
    FORMAT = MSSQL_ADO
    MSSQL_ADO_COMMAND_TIMEOUT = 30
    MSSQL_ADO_NAMED_CONNECTION = CubeManager
    MSSQL_ADO_QUERY_FEATURE_TYPES_FOR_MERGE_FILTERS = Yes
    SQL_STATEMENT:
      update dbo.Files
          set FMEJobIdDimensionUploaded = @Value(_job_id)
      where FileId = @Value(FileId)
    INITIATOR -> Output (output)
    <REJECTED> -> Rejected (output)
Note: We can't find the dimension file, abort process
SQLExecutor_14
    COMBINE_ATTRS = Result Attributes Only
    COMBINE_GEOM = Initiator Geometry Only
    DATASET = CubeManager
    FORMAT = MSSQL_ADO
    MSSQL_ADO_COMMAND_TIMEOUT = 30
    MSSQL_ADO_NAMED_CONNECTION = CubeManager
    MSSQL_ADO_QUERY_FEATURE_TYPES_FOR_MERGE_FILTERS = Yes
    SQL_STATEMENT:
      update dbo.Files
          set ErrorMessages = 'ERROR: Can''t find dimension file ("@Value(DimensionFile)")... Upload to cloud is not possible...'
      where FileId = @Value(FileId)
    INITIATOR -> Output (output)
    <REJECTED> -> Rejected (output)
Output (output)
Rejected (output)
Continue (output)

FME custom transformer Azure Blob to SQL DW

Parameters:
- httpserver =

Initiator (input)
    -> SQLExecutor_7 [INITIATOR]
Note: Check if we have any files to process
SQLExecutor_7
    COMBINE_ATTRS = Result Attributes Only
    COMBINE_GEOM = Initiator Geometry Only
    DATASET = CubeManager
    EXPOSED_ATTRIBUTE_LIST = "Total "
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = CubeManager
    MSSQL_ADO_QUERY_FEATURE_TYPES_FOR_MERGE_FILTERS = Yes
    SQL_STATEMENT:
      select  Count(*) as Total
      from dbo.[Files] inner join
      	CubeDimensions on files.CubeDimensionId = CubeDimensions.CubeDimensionId and
                            files.FileId = CubeDimensions.ActiveFile
      where  (dbo.[Files].FMEJobIdDimensionUploadedStatus=1
      and			isnull(dbo.[Files].FMEJobIdSQLDWCreated,0)=0
      and			isnull(dbo.[Files].FMEJobIdSQLDWCreatedStatus,0)  =0)
        and CubeDimensions.DeleteFlag =0
        and CubeDimensions.FmeConversionProcess != 'CreateDatabricksDimension.fmw'
    RESULT -> TestFilter
    <REJECTED> -> Rejected (output)
TestFilter
    DEFAULT_VALUE = <UNFILTERED>
    TEST_LIST = BOOL_OP,OR,COMPOSITE_TEST,<Unused>,TEST_CLAUSE,"TEST @Value(Total) > 0",RecordsToProccess
    RecordsToProccess -> SQLExecutor_12 [INITIATOR]
    <UNFILTERED> -> Continue (output)
Note: dbo.[Files].FMEJobIdDimensionUploadedStatus=1 / and dbo.[Files].FMEJobIdSQLDWCreated is null / and dbo.[Files].FMEJobIdSQLDWCreatedStatus =0
SQLExecutor_12
    COMBINE_ATTRS = Result Attributes Only
    COMBINE_GEOM = Initiator Geometry Only
    DATASET = CubeManager
    EXPOSED_ATTRIBUTE_LIST = FileId
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = CubeManager
    MSSQL_ADO_QUERY_FEATURE_TYPES_FOR_MERGE_FILTERS = Yes
    SQL_STATEMENT:
      select  dbo.[Files].[FileId]
      from dbo.[Files] inner join
      	CubeDimensions on files.CubeDimensionId = CubeDimensions.CubeDimensionId and
                            files.FileId = CubeDimensions.ActiveFile
      where  (dbo.[Files].FMEJobIdDimensionUploadedStatus=1
      and			isnull(dbo.[Files].FMEJobIdSQLDWCreated,0)=0
      and			isnull(dbo.[Files].FMEJobIdSQLDWCreatedStatus,0) =0 )
        and CubeDimensions.DeleteFlag =0
        and CubeDimensions.FmeConversionProcess != 'CreateDatabricksDimension.fmw'
    RESULT -> DynamicJobSubmitter_4
    <REJECTED> -> Rejected (output)
DynamicJobSubmitter_4
    FILEID = @Value(FileId)
    FMECONVERSIONPROCESS = CreateVectorDimensionDatabricks.fmw
    Repository = Cube Dimension Workspaces
    httpserver = $(httpserver)
    tmtag = oneengine
    Succeeded -> SQLExecutor_8 [INITIATOR]
    Failed -> Rejected (output)
Note: Tell database what JobId is doing the work
SQLExecutor_8
    COMBINE_ATTRS = Result Attributes Only
    COMBINE_GEOM = Initiator Geometry Only
    DATASET = CubeManager
    FORMAT = MSSQL_ADO
    MSSQL_ADO_COMMAND_TIMEOUT = 30
    MSSQL_ADO_NAMED_CONNECTION = CubeManager
    MSSQL_ADO_QUERY_FEATURE_TYPES_FOR_MERGE_FILTERS = Yes
    SQL_STATEMENT:
      update dbo.Files
          set FMEJobIdSQLDWCreated = @Value(_job_id)
      where FileId = @Value(FileId)
    INITIATOR -> Output (output)
    <REJECTED> -> Rejected (output)
Output (output)
Rejected (output)
Continue (output)
